Attribute VB_Name = "Module1"
Sub Main()
    UserForm.Show vbModeless
End Sub

Attribute VB_Name = "UserForm"
Attribute VB_Base = "0{C9C25912-72BD-4379-A74E-198EDAFB2B83}{570C824A-CB74-490E-AFEF-0D6C47169ECC}"
Attribute VB_GlobalNameSpace = False
Attribute VB_Creatable = False
Attribute VB_PredeclaredId = True
Attribute VB_Exposed = False
Attribute VB_TemplateDerived = False
Attribute VB_Customizable = False
Private Sub InitializeLevel(myCombo As ComboBox)
    Dim myLevel As Level
    
    For Each myLevel In ActiveModelReference.Levels
        myCombo.AddItem myLevel.Name
    Next
End Sub

Private Sub CommandButton_Calculate_Click()
    CentrelineByShapes
End Sub

Private Sub UserForm_DblClick(ByVal Cancel As MSForms.ReturnBoolean)
        InitializeLevel UserForm.ComboBox_Level
End Sub

Private Sub UserForm_Initialize()
    InitializeLevel UserForm.ComboBox_Level
End Sub

Private Sub CentrelineByShapes()
    Dim myEnum As ElementEnumerator
 '   Dim ComplexString As ElementEnumerator
    Dim myFilter As New ElementScanCriteria
    Dim Centroid() As Point3d
    Dim mCentreline As LineElement
    ReDim Centroid(0)
    
    Dim i As Long ' Количество Linestring
    

    myFilter.ExcludeAllTypes
    myFilter.ExcludeAllLevels
    
    myFilter.IncludeLevel ActiveDesignFile.Levels(UserForm.ComboBox_Level.Text)
    myFilter.IncludeType msdElementTypeShape
 '   myFilter.IncludeType msdElementTypeComplexString
    
    Set myEnum = ActiveModelReference.Scan(myFilter)
    
    While myEnum.MoveNext
        Select Case myEnum.Current.Type
            Case msdElementTypeShape
            Centroid(UBound(Centroid)) = myEnum.Current.AsShapeElement.Centroid
            ReDim Preserve Centroid(UBound(Centroid) + 1)
        End Select
    
    Wend
    ReDim Preserve Centroid(UBound(Centroid) - 1)
    Set mCentreline = CreateLineElement1(Nothing, Centroid)
    ActiveModelReference.AddElement mCentreline
    mCentreline.Redraw
'MsgBox "Длинна: " & FormatNumber(Round(l, 2), CInt(2), vbTrue, vbFalse, vbTrue) & " м" & vbCr & "LineString: " & i & vbCr & "ComplexChain: " & j & vbCr & "Line: " & k

End Sub
