Attribute VB_Name = "LineStringToLine"
Option Explicit

 Sub LineStringToLine(LevelName As String)
    Dim myFilter As New ElementScanCriteria
    Dim MyEnum As ElementEnumerator
    Dim StartPoint As Point3d
    Dim EndPoint As Point3d
    Dim Myline As LineElement
    Dim i As Long ' Счетчик
    myFilter.ExcludeAllTypes
    myFilter.ExcludeAllLevels
    
    myFilter.IncludeType msdElementTypeLineString
    myFilter.IncludeLevel ActiveModelReference.Levels(LevelName)
    
    i = 0
    Set MyEnum = ActiveModelReference.Scan(myFilter)
        While MyEnum.MoveNext
            If MyEnum.Current.AsLineElement.VerticesCount = 2 Then
                StartPoint = MyEnum.Current.AsLineElement.Vertex(1)
                EndPoint = MyEnum.Current.AsLineElement.Vertex(2)
                ActiveModelReference.RemoveElement MyEnum.Current
                MyEnum.Current.Redraw
                Set Myline = CreateLineElement2(MyEnum.Current, StartPoint, EndPoint)
                ActiveModelReference.AddElement Myline
                i = i + 1
            End If
        Wend
    UserForm_LineStringToLine.Label_LineCount = i
End Sub

Attribute VB_Name = "Module1"
Option Explicit

Sub Main()
    UserForm_LineStringToLine.Show vbModeless
End Sub

Attribute VB_Name = "UserForm_LineStringToLine"
Attribute VB_Base = "0{12945AF7-194C-4811-ADAA-9C9854A93A67}{9F214466-850E-4F47-967A-40BBE0837D72}"
Attribute VB_GlobalNameSpace = False
Attribute VB_Creatable = False
Attribute VB_PredeclaredId = True
Attribute VB_Exposed = False
Attribute VB_TemplateDerived = False
Attribute VB_Customizable = False
Option Explicit

Private Sub CommandButton_LineStringToLine_Click()
    LineStringToLine.LineStringToLine (UserForm_LineStringToLine.ComboBox_Levels.Text)
End Sub

Private Sub UserForm_Click()

End Sub

Private Sub UserForm_Initialize()
Dim myLevel As Level
Dim MyModel As ModelReference
    Set MyModel = ActiveDesignFile.DefaultModelReference
        For Each myLevel In MyModel.Levels
            ComboBox_Levels.AddItem myLevel.Name
        Next
End Sub
