Attribute VB_Name = "Module1"
Option Explicit
Public myText As TextElement
Public gDate As TextElement
Public sBoundary As Range3d
Public drobLine As LineElement
Sub Main()
    Myform.Show vbModeless
End Sub

'Public Sub CellToPoint()
'    Dim MyEnum As ElementEnumerator
'    Dim myFilter As New ElementScanCriteria
'    Dim MyCell As CellElement
'    Dim myText As TextElement
'    Dim PointInsert As Point3d
'
'    myFilter.ExcludeAllTypes
'    myFilter.IncludeType msdElementTypeLine
'
'    Set MyEnum = ActiveModelReference.Scan(myFilter)
'
'    While MyEnum.MoveNext
'        If MyEnum.Current.Level.IsDisplayedInView(ActiveDesignFile.Views.Item(1)) = True Then
'            Set MyCell = CreateCellElement3(Myform.cmbCell.Text, MyEnum.Current.AsLineElement.Vertex(1), True)
'            MyCell.Level = ActiveModelReference.Levels.Find(ActiveSettings.Level.Name)
'            ActiveModelReference.AddElement MyCell
'            MyCell.Redraw
'
'            PointInsert.X = MyEnum.Current.AsLineElement.Vertex(1).X + CDbl(Myform.tbOX.Text)
'            PointInsert.Y = MyEnum.Current.AsLineElement.Vertex(1).Y + CDbl(Myform.tbOY.Text)
'            PointInsert.Z = MyEnum.Current.AsLineElement.Vertex(1).Z
'
'            ActiveModelReference.RemoveElement MyEnum.Current.AsLineElement
'            MyEnum.Current.AsLineElement.Redraw
'
'            If Myform.CheckBox_Draw_height.Value = True Then
'                Set myText = CreateTextElement1(Nothing, FormatNumber(Round(CStr(PointInsert.Z), CInt(Myform.tbR.Text)), CInt(Myform.tbR.Text), vbTrue, vbTrue, vbFalse), PointInsert, Matrix3dIdentity)
'                myText.Level = ActiveModelReference.Levels.Find(ActiveSettings.Level.Name)
'                ActiveModelReference.AddElement myText
'                myText.Redraw
'            End If
'        End If
'    Wend
'End Sub

Attribute VB_Name = "Myform"
Attribute VB_Base = "0{21DCD2EB-E8A0-4282-BFAB-AABC16FFB96A}{C1ABF552-E5D1-4DC1-B7AB-3A21D3630013}"
Attribute VB_GlobalNameSpace = False
Attribute VB_Creatable = False
Attribute VB_PredeclaredId = True
Attribute VB_Exposed = False
Attribute VB_TemplateDerived = False
Attribute VB_Customizable = False
Option Explicit

'Private Sub CheckBox_Draw_height_Change()
'    If CheckBox_Draw_height.Value = True Then
'        CheckBox_Gidro_Date.Value = False
'    End If
'End Sub


Private Sub CheckBox_Gidro_Date_Change()
    If CheckBox_Gidro_Date.Value = True Then
        TextBox_DateForGidro.Enabled = True
        CheckBox_Draw_height.Value = False
        ComboBoxJustification.Value = ComboBoxJustification.List(0)
    Else
        TextBox_DateForGidro.Enabled = False
        CheckBox_Draw_height.Value = True
    End If
        
End Sub


Private Sub CheckBox_set_Z_Change()
    If CheckBox_set_Z.Value = True Then
        TextBox_setZ.Enabled = True
    Else: TextBox_setZ.Enabled = False
    End If
    
End Sub
Private Sub cmbPlace_Click()
    CommandState.StartPrimitive New PCE_PlaceCell, True
   ' PlaceHB
End Sub

Private Sub CommandButton_point_to_cell_Click()
    Module1.CellToPoint
End Sub

Private Sub CommandButton_z_by_text_Click()
    TextbyHeight
End Sub

Private Sub TextbyHeight()
    Dim myTxt As TextElement
    Dim tOr As Point3d
    Dim enumtxt As TextElement
    Dim i As Long
    Dim MyEnum As ElementEnumerator
    
    Set MyEnum = ActiveModelReference.GetSelectedElements
    
    While MyEnum.MoveNext
    If MyEnum.Current.AsTextElement.Origin.Z <> CDbl(MyEnum.Current.AsTextElement.Text) Then
        tOr.Z = CDbl(MyEnum.Current.AsTextElement.Text) - MyEnum.Current.AsTextElement.Origin.Z
             MyEnum.Current.AsTextElement.Move tOr
             MyEnum.Current.AsTextElement.Rewrite
             MyEnum.Current.AsTextElement.Redraw
        i = i + 1
      End If
    Wend
    MsgBox "Поднято: " & i
    i = 0
End Sub

Private Sub Label13_Click()

End Sub

Private Sub obP_Change()
    If obP.Value = True Then tbLW.Enabled = True
End Sub
Private Sub opCell_Change()
    If opCell.Value = True Then
        UserForm_Initialize
        tbLW.Enabled = False
    End If
End Sub
Private Sub opSCell_Change()
    Dim MyCellEnum As CellInformationEnumerator
    Dim MyCell As CellInformation
    cmbCell.Clear
    If opSCell.Value = True Then
        If IsCellLibraryAttached Then
            tbLW.Enabled = False
            Set MyCellEnum = Application.GetCellInformationEnumerator(True, False)
            While MyCellEnum.MoveNext
                Set MyCell = MyCellEnum.Current
                    If MyCell.IsShared Then cmbCell.AddItem MyCell.Name
            Wend
        Else
        MsgBox "Библиотека Cell не подключена", vbOKOnly + vbCritical
        opSCell.Value = True
    End If
    End If
End Sub

Private Sub UserForm_Initialize()
    InitializeCellsAsAttach cmbCell
    InitializeJustification ComboBoxJustification
    InitializeFontName ComboBox_Fonts
    InitializeLevels ComboBoxLeveOfPiket
End Sub
Sub PlaceHB()
    Dim myCIQ As CadInputQueue
    Dim myCIM As CadInputMessage
    Set myCIQ = CadInputQueue
    Dim MsgResp As VbMsgBoxResult
    Dim mP As Point3d
'---------------------- Цикл захвата точки и установки цела и подписи высоты -------------
    Do While True
        CommandState.StartDefaultCommand
        On Error Resume Next
        Set myCIM = myCIQ.GetInput
        If Err.Number <> 0 Then Exit Do
        Select Case myCIM.InputType
            Case msdCadInputTypeDataPoint
                mP = myCIM.Point
                If (Round(CStr(mP.Z), CInt(tbR.Text)) - Int(Round(CStr(mP.Z)))) = 0 Then
                    MsgResp = MsgBox("Целое значение высоты: " & FormatNumber(Round(CStr(mP.Z), CInt(tbR.Text)), CInt(tbR.Text), vbTrue, vbTrue, vbFalse) & ". Установить отметку?", vbYesNo + vbExclamation)
                Select Case MsgResp
                    Case VbMsgBoxResult.vbYes
                        PlaceHP mP
                    Case VbMsgBoxResult.vbNo
                    Debug.Print " Отмена нанесения"
                End Select
                Else: PlaceHP mP
                End If
            Case msdCadInputTypeReset
                Exit Do
        End Select
        Err.Clear
    Loop
End Sub
Function PlaceHP(myP As Point3d)
    Dim mC As CellElement           'Cell
    Dim mSC As SharedCellElement    'SharedCell
    Dim mL As LineElement           'Точка
    Dim mT As TextElement           'Текст подписи высоты
    Dim pT As Point3d               'Точка расположения подписи отметки высоты
    
        pT.X = myP.X + CDbl(Myform.TextBox_offsetX.Text)
        pT.Y = myP.Y '+ CDbl(tbOY.Text)
        pT.Z = myP.Z
        
    If opCell.Value = True Then
        Set mC = CreateCellElement3(cmbCell.Text, myP, True)
        mC.Level = ActiveModelReference.Levels.Find(ActiveSettings.Level.Name)
        ActiveModelReference.AddElement mC
        mC.Redraw
    ElseIf opSCell.Value = True Then
        Set mSC = CreateSharedCellElement3(cmbCell.Text, myP, True)
        ActiveModelReference.AddElement mSC
        mSC.Redraw
    ElseIf obP.Value = True Then
        Set mL = CreateLineElement2(Nothing, myP, myP)
        mL.LineWeight = CDbl(tbLW.Text)
        ActiveModelReference.AddElement mL
        mL.Redraw
    End If
        Set mT = CreateTextElement1(Nothing, FormatNumber(Round(CStr(myP.Z), CInt(tbR.Text)), CInt(tbR.Text), vbTrue, vbTrue, vbFalse), pT, Matrix3dIdentity)
        SetStyleText mT
        
'        ActiveModelReference.AddElement mT
'        mT.Redraw
End Function
Private Sub SetStyleText(ByRef mText As TextElement)
    Dim mPoint As Point3d
    
    mText.TextStyle.Height = CDbl(Myform.TextBox_TextHeight.Text)
    mText.TextStyle.Width = CDbl(Myform.TextBox_TextWidth.Text)
    mText.TextStyle.Font = ActiveDesignFile.Fonts(Myform.ComboBox_Fonts.Text)
    mText.TextStyle.Justification = msdTextJustificationLeftBottom
    
    Select Case Myform.ComboBoxJustification.Value
            Case "Right Top"
              '  mText.Move Point3dFromXY(0, 0)
            Case "Right Center"
                mText.Move Point3dFromXY(0, CDbl(Myform.TextBox_TextHeight.Text) * -0.5)
            Case "Right Bottom"
                mText.Move Point3dFromXY(0, -CDbl(Myform.TextBox_TextHeight.Text))
    End Select
    ActiveModelReference.AddElement mText
    mText.Redraw
End Sub
Private Sub InitializeJustification(mComboBox As ComboBox)
    mComboBox.Clear
    mComboBox.AddItem "Right Top"
    mComboBox.AddItem "Right Center"
    mComboBox.AddItem "Right Bottom"
    mComboBox.Value = mComboBox.List(1)
End Sub
Private Sub InitializeFontName(mComboBox As ComboBox)
    Dim MyModel As ModelReference
    Dim myFont As Font
    mComboBox.Clear
    Set MyModel = ActiveDesignFile.DefaultModelReference
        For Each myFont In MyModel.DesignFile.Fonts
            mComboBox.AddItem myFont.Name
        Next
End Sub
Private Sub InitializeLevels(mComboBox As ComboBox)
  Dim myLevel As Level

  mComboBox.Clear
  For Each myLevel In ActiveDesignFile.Levels
    mComboBox.AddItem myLevel.Name
  Next
End Sub
Private Sub InitializeCellsAsAttach(mCmboBox As ComboBox)
    Dim MyCellEnum As CellInformationEnumerator
    Dim MyCell As CellInformation
    
    mCmboBox.Clear
        If IsCellLibraryAttached Then
            Set MyCellEnum = Application.GetCellInformationEnumerator(True, False)
            While MyCellEnum.MoveNext
                Set MyCell = MyCellEnum.Current
                If Not MyCell.IsShared Then mCmboBox.AddItem MyCell.Name
            Wend
        Else: MsgBox "Библиотека Cell не подключена", vbOKOnly
        End If
End Sub
Sub DrawDate()

Attribute VB_Name = "PCE_PlaceCell"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private mC As CellElement           'Cell
Private mSC As SharedCellElement    'SharedCell
Private mL As LineElement           'Точка
'Private CellName As String
'Private myText As TextElement
Private PointInsert As Point3d
Implements IPrimitiveCommandEvents

Private Sub IPrimitiveCommandEvents_Cleanup()

End Sub

Private Sub IPrimitiveCommandEvents_DataPoint(Point As Point3d, ByVal View As View)
    Dim tmpPoint As Point3d
    
'    Dim MyCell As CellElement
'    Set MyCell = CreateCellElement3(CellName, Point, True)
'    MyCell.Level = ActiveDesignFile.Levels.Find(ActiveSettings.Level.Name)
'    ActiveModelReference.AddElement MyCell
'    MyCell.Redraw
    tmpPoint = Point
    If Myform.CheckBox_set_Z.Value = True Then
        tmpPoint.Z = CDbl(Myform.TextBox_setZ.Text)
    End If
    If Myform.opCell.Value = True Then
        Set mC = CreateCellElement3(Myform.cmbCell.Text, tmpPoint, True)
        mC.Level = ActiveDesignFile.Levels.Find(Myform.ComboBoxLeveOfPiket.Text)
        ActiveModelReference.AddElement mC
        mC.Redraw
    ElseIf Myform.opSCell.Value = True Then
        Set mSC = CreateSharedCellElement3(Myform.cmbCell.Text, tmpPoint, True)
        ActiveModelReference.AddElement mSC
        mSC.Redraw
    ElseIf Myform.obP.Value = True Then
        Set mL = CreateLineElement2(Nothing, tmpPoint, tmpPoint)
        mL.LineWeight = CDbl(Myform.tbLW.Text)
        ActiveModelReference.AddElement mL
        mL.Redraw
    End If
    If Myform.CheckBox_DynamicTxt.Value = True Then
       ' Set myText = CreateTextElement1(Nothing, FormatNumber(Round(CStr(PointInsert.Z), CInt(Myform.tbR.Text)), CInt(Myform.tbR.Text), vbTrue, vbTrue, vbTrue), Point, Matrix3dIdentity)
       ActiveModelReference.AddElement myText
      ' myText.Redraw
       CommandState.StartPrimitive New PCE_PlaceTxt, True
    ElseIf Myform.CheckBox_Draw_height.Value = True Then
        ActiveModelReference.AddElement myText
        myText.Redraw
    ElseIf Myform.CheckBox_Gidro_Date.Value = True Then
        ActiveModelReference.AddElement myText
        ActiveModelReference.AddElement gDate
        ActiveModelReference.AddElement drobLine
        myText.Redraw
        gDate.Redraw
        drobLine.Redraw
    End If
  
   
End Sub

Private Sub IPrimitiveCommandEvents_Dynamics(Point As Point3d, ByVal View As View, ByVal DrawMode As MsdDrawingMode)
  '  Dim MyCell As CellElement
   ' Set MyCell = CreateCellElement3(CellName, Point, True)
   ' MyCell.Redraw DrawMode
    Dim tmpPoint As Point3d
    Dim offsetDate As Point3d
    Dim bndDate As Range3d
    Dim offsetDrob As Double
    
    
    tmpPoint = Point
    offsetDrob = 0.5
    If Myform.CheckBox_set_Z.Value = True Then
        tmpPoint.Z = CDbl(Myform.TextBox_setZ.Text)
    End If
    If Myform.opCell.Value = True Then
        Set mC = CreateCellElement3(Myform.cmbCell.Text, tmpPoint, True)
        mC.Level = ActiveDesignFile.Levels.Find(Myform.ComboBoxLeveOfPiket.Text)
       ' ActiveModelReference.AddElement mC
        mC.Redraw DrawMode
    ElseIf Myform.opSCell.Value = True Then
        Set mSC = CreateSharedCellElement3(Myform.cmbCell.Text, tmpPoint, True)
      '  ActiveModelReference.AddElement mSC
        mSC.Redraw DrawMode
    ElseIf Myform.obP.Value = True Then
        Set mL = CreateLineElement2(Nothing, tmpPoint, tmpPoint)
        mL.LineWeight = CDbl(Myform.tbLW.Text)
      '  ActiveModelReference.AddElement mL
        mL.Redraw DrawMode
    End If
    If Myform.CheckBox_Draw_height.Value = True Then
        PointInsert.X = Point.X + CDbl(Myform.TextBox_offsetX.Text)
        PointInsert.Y = Point.Y '+ CDbl(Myform.tbOY.Text)
        PointInsert.Z = tmpPoint.Z
        Set myText = CreateTextElement1(Nothing, FormatNumber(Round(CStr(PointInsert.Z), CInt(Myform.tbR.Text)), CInt(Myform.tbR.Text), vbTrue, vbTrue, vbFalse), PointInsert, Matrix3dIdentity)
        SetStyleText myText
        myText.Redraw DrawMode
    ElseIf Myform.CheckBox_Gidro_Date.Value = True Then
        
        Set myText = CreateTextElement1(Nothing, FormatNumber(Round(CStr(Point.Z), CInt(Myform.tbR.Text)), CInt(Myform.tbR.Text), vbTrue, vbTrue, vbFalse), Point, Matrix3dIdentity)
        Set gDate = CreateTextElement1(Nothing, Myform.TextBox_DateForGidro.Text, Point, Matrix3dIdentity)
        SetStyleText gDate
        SetStyleText myText
        bndDate = gDate.Boundary
        sBoundary = myText.Boundary
        If (bndDate.High.X - bndDate.Low.X) >= (sBoundary.High.X - sBoundary.Low.X) Then
            Set drobLine = CreateLineElement2(Nothing, Point3dFromXYZ(bndDate.Low.X, Point.Y, Point.Z), Point3dFromXYZ(bndDate.High.X, Point.Y, Point.Z))
            drobLine.Move Point3dFromXYZ(CDbl(Myform.TextBox_offsetX.Text), 0, 0)
            gDate.Move Point3dFromXYZ(CDbl(Myform.TextBox_offsetX.Text), -(CDbl(Myform.TextBox_TextHeight.Text) + offsetDrob), 0)
            myText.Move Point3dFromXYZ(CDbl(Myform.TextBox_offsetX.Text) + ((bndDate.High.X - bndDate.Low.X) - (sBoundary.High.X - sBoundary.Low.X)) * 0.5, offsetDrob, 0)
        Else
            Set drobLine = CreateLineElement2(Nothing, Point3dFromXYZ(sBoundary.Low.X, Point.Y, Point.Z), Point3dFromXYZ(sBoundary.High.X, Point.Y, Point.Z))
            drobLine.Move Point3dFromXYZ(CDbl(Myform.TextBox_offsetX.Text), 0, 0)
            gDate.Move Point3dFromXYZ(CDbl(Myform.TextBox_offsetX.Text) + (-(bndDate.High.X - bndDate.Low.X) + (sBoundary.High.X - sBoundary.Low.X)) * 0.5, -(CDbl(Myform.TextBox_TextHeight.Text) + offsetDrob), 0)
            myText.Move Point3dFromXYZ(CDbl(Myform.TextBox_offsetX.Text), offsetDrob, 0)
        End If
        
        gDate.Level = ActiveDesignFile.Levels.Find(Myform.ComboBoxLeveOfPiket.Text)
        drobLine.Level = ActiveDesignFile.Levels.Find(Myform.ComboBoxLeveOfPiket.Text)
        gDate.Redraw DrawMode
        drobLine.Redraw DrawMode
        myText.Redraw DrawMode
    End If
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
    CommandState.StartDynamics
    'CellName = Myform.cmbCell.Text
End Sub

Private Sub SetStyleText(ByRef mText As TextElement)
    Dim mPoint As Point3d
    
    mText.TextStyle.Height = CDbl(Myform.TextBox_TextHeight.Text)
    mText.TextStyle.Width = CDbl(Myform.TextBox_TextWidth.Text)
    mText.TextStyle.Font = ActiveDesignFile.Fonts(Myform.ComboBox_Fonts.Text)
    mText.TextStyle.Justification = msdTextJustificationLeftBottom
    mText.Level = ActiveDesignFile.Levels.Find(Myform.ComboBoxLeveOfPiket.Text)
    
    Select Case Myform.ComboBoxJustification.Value
            Case "Right Top"
              '  mText.Move Point3dFromXY(0, 0)
            Case "Right Center"
                mText.Move Point3dFromXY(0, CDbl(Myform.TextBox_TextHeight.Text) * -0.5)
            Case "Right Bottom"
                mText.Move Point3dFromXY(0, -CDbl(Myform.TextBox_TextHeight.Text))
    End Select
'    ActiveModelReference.AddElement mText
'    mText.Redraw
End Sub

Attribute VB_Name = "PCE_PlaceTxt"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents
Private mTxt As Point3d

Private Sub IPrimitiveCommandEvents_Cleanup()

End Sub

Private Sub IPrimitiveCommandEvents_DataPoint(Point As Point3d, ByVal View As View)

myText.Move mTxt
myText.Rewrite
myText.Redraw
CommandState.StartDefaultCommand
End Sub

Private Sub IPrimitiveCommandEvents_Dynamics(Point As Point3d, ByVal View As View, ByVal DrawMode As MsdDrawingMode)
'Dim mTxt As Point3d

mTxt.X = Point.X - myText.Origin.X
mTxt.Y = Point.Y - myText.Origin.Y
mTxt.Z = myText.Origin.Z
myText.Move mTxt
myText.Redraw DrawMode
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
    CommandState.StartDynamics
End Sub
