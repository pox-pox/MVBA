Attribute VB_Name = "LCE_CutLines"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Dim FirstLine As Element
Dim SecondLine As Element
Dim AttrFirst As String
Dim AttrSecond As String
Dim desc As String
Dim FirstS() As String
Dim SecondS() As String
Dim prPointFirst As Point3d
Dim prPointSecond As Point3d
Dim LevelName(0 To 1) As String
Dim StartLeft As LineElement
Dim StartRight As LineElement
Dim EndLeft As LineElement
Dim EndRight As LineElement
Dim PointsLeft() As Point3d, PointsRight() As Point3d

Private Sub ILocateCommandEvents_Accept(ByVal Element As Element, Point As Point3d, ByVal View As View)
   
    CutLineByPoint FirstLine, prPointFirst, StartLeft, EndLeft
    CutLineByPoint SecondLine, prPointSecond, StartRight, EndRight
    DetectRH StartLeft, StartRight
    RailsToPoint StartLeft, StartRight, False
    
    If UserForm1.CheckBoxCutEnd.Value = True Then
        DetectRH EndLeft, EndRight
        RailsToPoint EndLeft, EndRight, True
    End If
    
    CommandState.StopDynamics
    UserForm1.Label_NumRail.Caption = ""
    CommandState.StartDefaultCommand
   
End Sub
Private Sub DetectRH(LeftLine As Element, RightLine As Element)
    Dim sideL As String
    Dim sideR As String
    Dim delta As Double
    
    delta = (LeftLine.AsLineElement.Length - RightLine.AsLineElement.Length) * 200 / (LeftLine.AsLineElement.Length + RightLine.AsLineElement.Length)
    
    If delta > CDbl(UserForm1.TextBox_DopuskCurve.Text) Then
        sideR = "L"
        sideL = "H"
        SetRihtovochnyi RightLine
    ElseIf delta < -CDbl(UserForm1.TextBox_DopuskCurve.Text) Then
        sideR = "H"
        sideL = "R"
        SetRihtovochnyi LeftLine
    Else
        sideL = "H"
        sideR = "L"
        SetRihtovochnyi RightLine
    End If
    
    UserForm1.AddLinkage LeftLine, UserForm1.Label_NumRail.Caption & "-" & sideL, ""
    UserForm1.AddLinkage RightLine, UserForm1.Label_NumRail.Caption & "-" & sideR, ""
End Sub

Private Sub SetRihtovochnyi(mLine As Element)
    mLine.LineWeight = 2
    mLine.Redraw
    
End Sub
Private Sub TransferLink(ByRef inElement As Element, ByRef outElement As Element)
    Dim atr As String
    Dim desc As String
    
    UserForm1.GetLinkage inElement, atr, desc
    UserForm1.AddLinkage outElement, atr, desc
End Sub
Private Sub DrawPoint(mPoint As LineElement, level As String)
    mPoint.level = ActiveDesignFile.Levels.Find(level)
    mPoint.Color = ByLevelColor
    mPoint.LineWeight = ByLevelLineWeight
    ActiveModelReference.AddElement mPoint
    mPoint.Redraw
End Sub

Private Sub ILocateCommandEvents_Cleanup()
    CommandState.StartDefaultCommand
End Sub

Private Sub ILocateCommandEvents_Dynamics(Point As Point3d, ByVal View As View, ByVal DrawMode As MsdDrawingMode)
    
    Dim cLine As LineElement
    CutLine Point
    Set cLine = CreateLineElement2(Nothing, prPointFirst, prPointSecond)
    cLine.LineWeight = 0
    cLine.Color = 1
    cLine.Redraw DrawMode
    
    Dim i As Long
    
    If UserForm1.CheckBoxDinamicVertex.Value = True Then ' Динамическая разбивка
        For i = 0 To UBound(PointsLeft)
            Set cLine = CreateLineElement2(Nothing, PointsLeft(i), PointsLeft(i))
            cLine.LineWeight = 4
            cLine.Color = 1
            cLine.Redraw DrawMode
        Next i
        For i = 0 To UBound(PointsRight)
            Set cLine = CreateLineElement2(Nothing, PointsRight(i), PointsRight(i))
            cLine.LineWeight = 4
            cLine.Color = 1
            cLine.Redraw DrawMode
        Next i
    End If
    
End Sub

Private Sub ILocateCommandEvents_LocateFailed()
    UserForm1.Label_NumRail.Caption = ""
    CommandState.StartDefaultCommand
End Sub

Private Sub ILocateCommandEvents_LocateFilter(ByVal Element As Element, Point As Point3d, Accepted As Boolean)
Dim Hit As Boolean

Accepted = False
    If Element.Type = msdElementTypeLineString Or Element.Type = msdElementTypeComplexString Then
        Set FirstLine = Element
        UserForm1.GetLinkage FirstLine, AttrFirst, desc
        LevelName(0) = desc
        Accepted = True
        
        Dim mEnum As ElementEnumerator
        Dim mFilter As New ElementScanCriteria
        
        mFilter.ExcludeAllTypes
        mFilter.IncludeType msdElementTypeLineString
        mFilter.IncludeType msdElementTypeComplexString
        Set mEnum = ActiveModelReference.Scan(mFilter)
        
        FirstS() = Split(AttrFirst, "-")
        While mEnum.MoveNext And Not Hit
            UserForm1.GetLinkage mEnum.Current, AttrSecond, desc
            Debug.Print AttrSecond
            SecondS() = Split(AttrSecond, "-")
            If UBound(SecondS) >= 0 Then
                Debug.Print SecondS(0)
                If FirstS(0) = SecondS(0) Then
                    If FirstLine.FilePosition <> mEnum.Current.FilePosition Then
                        If IsSideRail(FirstLine.AsLineElement, mEnum.Current.AsLineElement) Then
                            Set SecondLine = mEnum.Current
                            LevelName(1) = desc
                            Hit = True
                            UserForm1.Label_NumRail.Caption = FirstS(0)
                            If UserForm1.CheckBoxDinamicVertex.Value = True Then ' Динамическая разбивка
                                UserForm1.IsLeftRight FirstLine, SecondLine
                                UserForm1.LineToVertexByStep FirstLine, PointsLeft, True
                                UserForm1.GetRightPoint SecondLine, PointsLeft, PointsRight, True
                            End If
                        End If
                    End If
                End If
            End If
        Wend
    End If
    
    
    CommandState.StartDynamics
End Sub

Private Sub ILocateCommandEvents_LocateReset()
    UserForm1.Label_NumRail.Caption = ""
    CommandState.StopDynamics
    CommandState.StartDefaultCommand
End Sub

Private Sub ILocateCommandEvents_Start()
    UserForm1.Label_NumRail.Caption = ""
End Sub

Private Sub CutLine(Point As Point3d)
    Dim i As Long
    Dim NumCutVertL As Long
    Dim NumCutVertR As Long
    
    Dim StartVertexL() As Point3d, StartVertexR() As Point3d
    Dim EndVertexL() As Point3d, EndVertexR() As Point3d
    
    UserForm1.IsLeftRight FirstLine, SecondLine
    
    UserForm1.Project_Point1 FirstLine, Point, prPointFirst
    UserForm1.Project_Point1 SecondLine, Point, prPointSecond
    NumCutVertL = FirstLine.AsLineElement.GetClosestSegment(prPointFirst)
    NumCutVertR = FirstLine.AsLineElement.GetClosestSegment(prPointSecond)
    
End Sub

Private Sub CutLineByPoint(mLine As Element, cPoint As Point3d, ByRef sLine As LineElement, ByRef eLine As LineElement)
    Dim StartLine() As Point3d
    Dim EndLine() As Point3d
    Dim i As Long
    Dim NVert As Long
    
    NVert = mLine.AsLineElement.GetClosestSegment(cPoint)
    
    For i = 0 To NVert
        RedimPreserve StartLine
        StartLine(i) = mLine.AsLineElement.Vertex(i + 1)
    Next i
    RedimPreserve StartLine
    StartLine(NVert + 1) = cPoint
    RedimPreserve EndLine
    EndLine(0) = cPoint
    For i = (NVert + 2) To mLine.AsLineElement.VerticesCount
        RedimPreserve EndLine
        EndLine(UBound(EndLine)) = mLine.AsLineElement.Vertex(i)
    Next i
        
    Set sLine = CreateLineElement1(Nothing, StartLine)
    Set eLine = CreateLineElement1(Nothing, EndLine)
    
'    Dim lName() As String
'    lName = Split(mLine.level.Name, "_")
'
'    If lName(UBound(lName)) <> "cut" Then
'        lName(0) = "_" & mLine.level.Name & "_cut"
'    Else
'        lName(0) = mLine.level.Name
'    End If
    sLine.level = mLine.level
    eLine.level = mLine.level
    
    ActiveModelReference.AddElement sLine
    ActiveModelReference.AddElement eLine
    sLine.Redraw
    eLine.Redraw
    TransferLink mLine, eLine
    ActiveModelReference.RemoveElement mLine
    mLine.Redraw
    
End Sub
Sub RedimPreserve(ByRef mB() As Point3d)
    Dim i As Long
    On Error Resume Next
    i = UBound(mB) + 1
    If Err.Number = 9 Then
        ReDim mB(0)
    Else: ReDim Preserve mB(i)
    End If
    Err.Clear
End Sub

Private Function IsSideRail(fLine As LineElement, sLine As LineElement) As Boolean
    Dim VectorR As Vector3d
    Dim VectorL As Vector3d
    Dim Response
    Dim Line As LineElement
    Dim pPoint() As Point3d
    Dim tempLine As LineElement
    
    VectorL = Vector3dSubtractPoint3dPoint3d(fLine.Vertex(3), fLine.Vertex(2))
    VectorL = Vector3dUnitPerpendicularXY(VectorL)
    VectorL = Vector3dScale(VectorL, 2)
    VectorR = Vector3dScale(VectorL, -1)
    
    Set Line = CreateLineElement2(Nothing, Point3dAdd(fLine.Vertex(2), Point3dFromVector3d(VectorL)), Point3dAdd(fLine.Vertex(2), Point3dFromVector3d(VectorR)))
    pPoint = sLine.AsIntersectableElement.GetIntersectionPoints(Line, Matrix3dIdentity)
    
    If UBound(pPoint) >= 0 Then
        IsSideRail = True
    Else
        IsSideRail = False
    End If
    
End Function

Private Sub RailsToPoint(LeftLine As LineElement, RightLine As LineElement, HitEnd As Boolean)
    
    Dim atr As String, desc As String
    Dim Num As String
        
    UserForm1.LineToVertexByStep LeftLine, PointsLeft, HitEnd
    
    UserForm1.GetLinkage LeftLine, atr, desc
    Num = UserForm1.Label_NumRail.Caption
    If Num <> "" Then
        UserForm1.DrawPoints PointsLeft, UserForm1.CheckLevel(CStr(Num) & " " & "путь левый рельс (точки- номера-коды)", 0).Name, atr
        UserForm1.AddLinkage LeftLine, atr, CStr(Num) & " " & "путь левый рельс (точки- номера-коды)"
        UserForm1.GetLinkage RightLine, atr, desc
        UserForm1.GetRightPoint RightLine, PointsLeft, PointsRight, HitEnd
        UserForm1.DrawPoints PointsRight, UserForm1.CheckLevel(CStr(Num) & " " & "путь правый рельс (точки- номера-коды)", 8).Name, atr
        UserForm1.AddLinkage RightLine, atr, CStr(Num) & " " & "путь правый рельс (точки- номера-коды)"
    Else
        MsgBox "Номер пути не задан"
    End If
End Sub

Function CheckLevel(LevelName As String, i As Integer) As level
    Dim MyLevel As level
    On Error Resume Next
    
    Set CheckLevel = ActiveDesignFile.Levels(LevelName)
    If Err.Number <> 0 And LevelName <> "" Then
         Set MyLevel = ActiveDesignFile.AddNewLevel(LevelName)
         MyLevel.ElementLineWeight = 0
         MyLevel.ElementColor = 3
         ActiveDesignFile.Levels.Rewrite
         MsgBox "Создан слой: " & LevelName
         Set CheckLevel = MyLevel
    End If
    Err.Clear
End Function

Attribute VB_Name = "LCE_Edit"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private Const attrId As Long = 22352
Dim editElement As LineElement
Dim mAtr As TextElement
Dim textOrigin As Point3d
Dim Hit As Boolean


Private Sub ILocateCommandEvents_Accept(ByVal Element As Element, Point As Point3d, ByVal View As View)
    
    If UserForm1.TextBox_Attribut.Text <> "[NULL]" Then
        UserForm1.AddLinkage editElement, UserForm1.TextBox_Attribut.Text, UserForm1.TextBox_Description.Text
        If Element.Type = msdElementTypeLine Then
            ActiveModelReference.AddElement mAtr
            mAtr.Redraw
        End If
        UserForm1.TextBox_Attribut.Text = ""
        UserForm1.TextBox_Description.Text = ""
        
    End If
    CommandState.StopDynamics
    CommandState.StartDefaultCommand
End Sub

Private Sub ILocateCommandEvents_Cleanup()

End Sub

Private Sub ILocateCommandEvents_Dynamics(Point As Point3d, ByVal View As View, ByVal DrawMode As MsdDrawingMode)
    Set mAtr = CreateTextElement1(Nothing, UserForm1.TextBox_Attribut.Text, textOrigin, Matrix3dIdentity)
    SetTextAtribut mAtr
    mAtr.Redraw DrawMode
End Sub

Private Sub ILocateCommandEvents_LocateFailed()
'    ActiveModelReference.AddElement mAtr
'    mAtr.Redraw
  '  CommandState.StartLocate Me
    CommandState.StartDefaultCommand
    UserForm1.TextBox_Attribut.Text = ""
    UserForm1.TextBox_Description.Text = ""
    
End Sub

Private Sub ILocateCommandEvents_LocateFilter(ByVal Element As Element, Point As Point3d, Accepted As Boolean)
    Dim Attribut As String
    Dim Description As String
    Accepted = False
        If Element.Type = msdElementTypeLineString Or Element.Type = msdElementTypeLine Then
            Accepted = True
            Set editElement = Element.AsLineElement
            
            UserForm1.GetLinkage editElement, Attribut, Description
            UserForm1.TextBox_Attribut.Text = Attribut
            UserForm1.TextBox_Description.Text = Description
             
            If Element.Type = msdElementTypeLine Then
                If Not Hit Then
                    EditAtribut Element.AsLineElement
                    textOrigin = Element.AsLineElement.startPoint
                    Hit = True
                End If
            End If
            CommandState.StartDynamics
        End If
End Sub

Private Sub ILocateCommandEvents_LocateReset()
        
    UserForm1.TextBox_Attribut.Text = ""
    UserForm1.TextBox_Description.Text = ""
    CommandState.StartDefaultCommand
    
End Sub

Private Sub ILocateCommandEvents_Start()
    UserForm1.TextBox_Attribut.Text = ""
    UserForm1.TextBox_Description.Text = ""
    'CommandState.EnableAccuSnap
End Sub

Private Sub EditAtribut(mPoint As LineElement)
    Dim mEnum As ElementEnumerator
    Dim mFilter As New ElementScanCriteria
    
    mFilter.ExcludeAllLevels
    mFilter.ExcludeAllTypes
    
    mFilter.IncludeLevel ActiveSettings.level
    mFilter.IncludeType msdElementTypeText
    
    Set mEnum = ActiveModelReference.Scan(mFilter)
    
    While mEnum.MoveNext
        If Point3dEqualTolerance(mPoint.startPoint, mEnum.Current.AsTextElement.Origin, 0.01) Then
            ActiveModelReference.RemoveElement mEnum.Current
            mEnum.Current.Redraw
            
        End If
    Wend
End Sub
 
Private Sub SetTextAtribut(ByRef MText As TextElement)
    MText.TextStyle.Justification = msdTextJustificationLeftBottom
    MText.TextStyle.Height = CDbl(UserForm1.TextBox_SizeAtr.Text)
    
    MText.TextStyle.Width = CDbl(UserForm1.TextBox_SizeAtr.Text)
    MText.TextStyle.Font = ActiveDesignFile.Fonts("Arial")
    MText.Color = 0
    MText.level = ActiveSettings.level
End Sub

Attribute VB_Name = "LCE_PointOnRails"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Dim FirstLine As Element
Dim SecondLine As Element
Dim AttrFirst As String
Dim AttrSecond As String
Dim desc As String
Dim FirstS() As String
Dim SecondS() As String
Dim AtributF As TextElement
Dim AtributS As TextElement
Dim prPointFirst As Point3d
Dim prPointSecond As Point3d
Dim newAtributFirst As String
Dim newAtributSecond As String
Dim LevelName(0 To 1) As String

Private Sub ILocateCommandEvents_Accept(ByVal Element As Element, Point As Point3d, ByVal View As View)
    Dim prPointLine As LineElement
    
        Set prPointLine = CreateLineElement2(Nothing, prPointFirst, prPointFirst)
        DrawPoint prPointLine, LevelName(0)
        UserForm1.AddLinkage prPointLine, newAtributFirst, UserForm1.TextBox_Description.Text
        
        Set prPointLine = CreateLineElement2(Nothing, prPointSecond, prPointSecond)
        DrawPoint prPointLine, LevelName(1)
        
        ActiveModelReference.AddElement AtributF
        ActiveModelReference.AddElement AtributS
        AtributF.Redraw
        AtributS.Redraw
        UserForm1.AddLinkage prPointLine, newAtributSecond, ""
    
    CommandState.StopDynamics
    CommandState.StartDefaultCommand
   
End Sub

Private Sub DrawPoint(mPoint As LineElement, level As String)
    mPoint.level = ActiveDesignFile.Levels.Find(level)
    mPoint.Color = ByLevelColor
    mPoint.LineWeight = ByLevelLineWeight
    ActiveModelReference.AddElement mPoint
    mPoint.Redraw
End Sub

Private Sub ILocateCommandEvents_Cleanup()
    CommandState.StartDefaultCommand
End Sub

Private Sub ILocateCommandEvents_Dynamics(Point As Point3d, ByVal View As View, ByVal DrawMode As MsdDrawingMode)
    Dim prPointLine As LineElement
    
        UserForm1.Project_Point1 FirstLine, Point, prPointFirst
        Set prPointLine = CreateLineElement2(Nothing, prPointFirst, prPointFirst)
        prPointLine.LineWeight = 6
        prPointLine.Redraw DrawMode
        UserForm1.Project_Point1 SecondLine, Point, prPointSecond
        Set prPointLine = CreateLineElement2(Nothing, prPointSecond, prPointSecond)
        prPointLine.LineWeight = 6
        prPointLine.Redraw DrawMode
        
        If FirstS(1) = "H" Then
            newAtributFirst = AttrFirst
            newAtributSecond = UserForm1.TextBox_Attribut.Text
        Else
            newAtributFirst = UserForm1.TextBox_Attribut.Text
            newAtributSecond = AttrSecond
        End If
        
        Set AtributF = CreateTextElement1(Nothing, newAtributFirst, prPointFirst, Matrix3dIdentity)
        SetTextAtribut AtributF, LevelName(0)
        AtributF.Redraw DrawMode
        Set AtributS = CreateTextElement1(Nothing, newAtributSecond, prPointSecond, Matrix3dIdentity)
        SetTextAtribut AtributS, LevelName(1)
        AtributS.Redraw DrawMode
End Sub

Private Sub ILocateCommandEvents_LocateFailed()
    CommandState.StartDefaultCommand
End Sub

Private Sub ILocateCommandEvents_LocateFilter(ByVal Element As Element, Point As Point3d, Accepted As Boolean)
Dim Hit As Boolean

Accepted = False
    If Element.Type = msdElementTypeLineString Or Element.Type = msdElementTypeComplexString Then
        Set FirstLine = Element
        UserForm1.GetLinkage FirstLine, AttrFirst, desc
        LevelName(0) = desc
        Accepted = True
        
        Dim mEnum As ElementEnumerator
        Dim mFilter As New ElementScanCriteria
        
        mFilter.ExcludeAllTypes
        mFilter.IncludeType msdElementTypeLineString
        mFilter.IncludeType msdElementTypeComplexString
        Set mEnum = ActiveModelReference.Scan(mFilter)
        
        FirstS() = Split(AttrFirst, "-")
        While mEnum.MoveNext And Not Hit
            UserForm1.GetLinkage mEnum.Current, AttrSecond, desc
            Debug.Print AttrSecond
            SecondS() = Split(AttrSecond, "-")
            If UBound(SecondS) >= 0 Then
                Debug.Print SecondS(0)
                If FirstS(0) = SecondS(0) Then
                    If FirstLine.FilePosition <> mEnum.Current.FilePosition Then
                        If IsSideRail(FirstLine.AsLineElement, mEnum.Current.AsLineElement) Then
                            Set SecondLine = mEnum.Current
                            LevelName(1) = desc
                            Hit = True
                        End If
                    End If
                End If
            End If
        Wend
    End If
    
    If FirstS(1) = "H" Then
        UserForm1.TextBox_Attribut.Text = AttrSecond
    Else
        UserForm1.TextBox_Attribut.Text = AttrFirst
    End If
    UserForm1.TextBox_Attribut.Text = UserForm1.TextBox_Attribut.Text & "-" & UserForm1.GetNumRail(UserForm1.ComboBox_Code.Text, 0) & UserForm1.TextBox_Number.Text
    CommandState.StartDynamics
End Sub

Private Sub ILocateCommandEvents_LocateReset()
    UserForm1.TextBox_Attribut.Text = ""
    UserForm1.TextBox_Description.Text = ""
    UserForm1.ComboBox_Code.Text = ""
    CommandState.StopDynamics
    CommandState.StartDefaultCommand
End Sub

Private Sub ILocateCommandEvents_Start()

End Sub

Private Sub SetTextAtribut(ByRef MText As TextElement, LevelName As String)
    MText.TextStyle.Justification = msdTextJustificationLeftBottom
    MText.TextStyle.Height = CDbl(UserForm1.TextBox_SizeAtr.Text)
    MText.TextStyle.Width = CDbl(UserForm1.TextBox_SizeAtr.Text)
    MText.TextStyle.Font = ActiveDesignFile.Fonts("Arial")
    MText.level = ActiveDesignFile.Levels.Find(LevelName)
    MText.Color = ByLevelColor
    
End Sub


Private Function IsSideRail(fLine As LineElement, sLine As LineElement) As Boolean
    Dim VectorR As Vector3d
    Dim VectorL As Vector3d
    
    Dim Line As LineElement
    Dim pPoint() As Point3d
    Dim tempLine As LineElement
    
    VectorL = Vector3dSubtractPoint3dPoint3d(fLine.Vertex(3), fLine.Vertex(2))
    VectorL = Vector3dUnitPerpendicularXY(VectorL)
    VectorL = Vector3dScale(VectorL, 2)
    VectorR = Vector3dScale(VectorL, -1)
    
    Set Line = CreateLineElement2(Nothing, Point3dAdd(fLine.Vertex(2), Point3dFromVector3d(VectorL)), Point3dAdd(fLine.Vertex(2), Point3dFromVector3d(VectorR)))
    pPoint = sLine.AsIntersectableElement.GetIntersectionPoints(Line, Matrix3dIdentity)
    
    
    If UBound(pPoint) >= 0 Then
        IsSideRail = True
    Else
        IsSideRail = False
    End If
    
End Function

Attribute VB_Name = "Module1"
Public Type TOR
    Point As Point3d
    side As String
    TrackNumber As Double
    dH As Double
End Type

Sub Main()
    UserForm1.Show vbModeless
End Sub

Attribute VB_Name = "PCE_Place_point"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents
Dim mPoint As LineElement
Dim mAtr As TextElement

Private Sub IPrimitiveCommandEvents_Cleanup()

End Sub

Private Sub IPrimitiveCommandEvents_DataPoint(Point As Point3d, ByVal View As View)
    ActiveModelReference.AddElement mPoint
    ActiveModelReference.AddElement mAtr
    mPoint.Redraw
    mAtr.Redraw
    UserForm1.AddLinkage mPoint, UserForm1.TextBox_Attribut.Text, UserForm1.TextBox_Description.Text

End Sub

Private Sub IPrimitiveCommandEvents_Dynamics(Point As Point3d, ByVal View As View, ByVal DrawMode As MsdDrawingMode)
        
    Set mPoint = CreateLineElement2(Nothing, Point, Point)
    mPoint.level = ActiveSettings.level
    mPoint.Color = ByLevelColor
    mPoint.LineWeight = ByLevelLineWeight
    
    mPoint.Redraw DrawMode
    Set mAtr = CreateTextElement1(Nothing, UserForm1.TextBox_Attribut.Text, Point, Matrix3dIdentity)
    SetTextAtribut mAtr
    mAtr.Redraw DrawMode
    
    
End Sub

Private Sub IPrimitiveCommandEvents_Keyin(ByVal Keyin As String)

End Sub

Private Sub IPrimitiveCommandEvents_Reset()
    
    CommandState.StartDefaultCommand
    
End Sub

Private Sub IPrimitiveCommandEvents_Start()
    CommandState.EnableAccuSnap
    On Error Resume Next
    CommandState.AccuDrawHints.Deactivate
    CommandState.StartDynamics
End Sub

Private Sub SetTextAtribut(ByRef MText As TextElement)
    MText.TextStyle.Justification = msdTextJustificationLeftBottom
    MText.TextStyle.Height = 0.15
    MText.TextStyle.Width = 0.15
    MText.TextStyle.Font = ActiveDesignFile.Fonts("Arial")
    MText.Color = 0
    MText.level = ActiveSettings.level
End Sub

Attribute VB_Name = "PCE_ProjectPoints"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents
Dim Rails() As Element

Private Sub IPrimitiveCommandEvents_Cleanup()

End Sub

Private Sub IPrimitiveCommandEvents_DataPoint(Point As Point3d, ByVal View As View)
    
End Sub

Private Sub IPrimitiveCommandEvents_Dynamics(Point As Point3d, ByVal View As View, ByVal DrawMode As MsdDrawingMode)
 Dim i As Integer
    Dim prPoint As Point3d
    Dim prPointLine As LineElement
    Dim mEnum As ElementEnumerator
    
    Set mEnum = ActiveModelReference.GetSelectedElements
    Rails = mEnum.BuildArrayFromContents
    
    For i = 0 To UBound(Rails)
        UserForm1.Project_Point1 Rails(i), Point, prPoint
        Set prPointLine = CreateLineElement2(Nothing, prPoint, prPoint)
        prPointLine.LineWeight = 8
        
        prPointLine.Redraw DrawMode
        
    Next i
    

End Sub

Private Sub IPrimitiveCommandEvents_Keyin(ByVal Keyin As String)

End Sub

Private Sub IPrimitiveCommandEvents_Reset()
    CommandState.StartDefaultCommand
End Sub

Private Sub IPrimitiveCommandEvents_Start()
    CommandState.StartDynamics
End Sub

Attribute VB_Name = "UserForm1"
Attribute VB_Base = "0{5E517B1F-A559-44F4-A739-04639F99687F}{AD91B4C9-9AE3-4179-A14A-0E2174CAE48B}"
Attribute VB_GlobalNameSpace = False
Attribute VB_Creatable = False
Attribute VB_PredeclaredId = True
Attribute VB_Exposed = False
Attribute VB_TemplateDerived = False
Attribute VB_Customizable = False

Private Const attrId As Long = 22352
Private Const attrId1 As Long = 22353

Private Sub InitializeLevels(mComboBox As ComboBox)
  Dim MyLevel As level

  mComboBox.Clear
  For Each MyLevel In ActiveDesignFile.Levels
    mComboBox.AddItem MyLevel.Name
  Next
End Sub
Private Sub ComboBox_Level_LP_DblClick(ByVal Cancel As MSForms.ReturnBoolean)
    InitializeLevels ComboBox_Level_LP
    InitializeLevels ComboBox_Level_RP
End Sub

Private Sub ComboBox_Level_RP_DblClick(ByVal Cancel As MSForms.ReturnBoolean)
    InitializeLevels ComboBox_Level_LP
    InitializeLevels ComboBox_Level_RP
End Sub

Private Sub CommandButton_DrawPoint_Click()
    CommandState.StartPrimitive New PCE_ProjectPoints, True
End Sub
Private Sub InizialazeCodes()
    ComboBox_Code.AddItem "N-начало пути"
    ComboBox_Code.AddItem "К-конец пути"
    ComboBox_Code.AddItem "S-изостык"
    ComboBox_Code.AddItem "T-остряк"
    ComboBox_Code.AddItem "V-хвост"
    ComboBox_Code.AddItem "RR-стык рамного рельса"
    ComboBox_Code.AddItem "US-уравнительный стык"
    ComboBox_Code.AddItem "OTH-прочие объекты"
End Sub

Private Sub InizialazeStep()
    ComboBox_StepByUchastok.AddItem "Участок пути (5м.)"
    ComboBox_StepByUchastok.AddItem "Платформа    (3м.)"
    ComboBox_StepByUchastok.AddItem "Стрелка      (2м.)"
    
    ComboBox_StepByUchastok = ComboBox_StepByUchastok.List(0)
End Sub


Private Sub ComboBox_Code_Change()
    Dim atr As String
    atr = TextBox_Attribut.Text
    TextBox_Attribut.Text = GetNumRail(atr, 0) & "-" & GetNumRail(atr, 1) & "-" & GetNumRail(ComboBox_Code.Text, 0) & TextBox_Number.Text
End Sub

Private Sub CommandButton_DrawAtr_Click()
    DrawAttr
End Sub

Private Sub CommandButton_ExportToExcel_Click()
    ExportToExcel
End Sub
Private Sub CommandButton_Object_Click()
    CommandState.StartLocate New LCE_Edit
End Sub
Private Sub CommandButton_PlacePoint_Click()
    CommandState.StartPrimitive New PCE_Place_point, True
End Sub
Private Sub CommandButton_PointOnRails_Click()
    CommandState.StartLocate New LCE_PointOnRails
End Sub
Private Sub CommandButton_projectPoints_Click()
    ProjectsPoints
End Sub

Private Sub CommandButton_Run_Click()
    RailsToPoint
End Sub

Private Sub RailsToPoint()
    Dim mEnum As ElementEnumerator
    Dim lineTemp() As Element
    Dim PointsLeft() As Point3d, PointsRight() As Point3d
    Dim LeftLine As LineElement
    Dim RightLine As LineElement
    Dim atr As String, desc As String
    Dim Num As String
    
    Set mEnum = ActiveModelReference.GetSelectedElements
    lineTemp = mEnum.BuildArrayFromContents
    
    If UBound(lineTemp) = 1 Then
            Set LeftLine = lineTemp(0).AsLineElement
            Set RightLine = lineTemp(1).AsLineElement
            
            IsLeftRight LeftLine, RightLine
            Set lineTemp(0) = LeftLine
            Set lineTemp(1) = RightLine
            LineToVertexByStep LeftLine, PointsLeft, CheckBox_EndLine.Value
            
            GetLinkage lineTemp(0), atr, desc
            Num = GetNumRail(atr, 0)
            If Num <> "" Then
                DrawPoints PointsLeft, CheckLevel(CStr(Num) & " " & "путь левый рельс (точки- номера-коды)", 0).Name, atr
                AddLinkage lineTemp(0), atr, CStr(Num) & " " & "путь левый рельс (точки- номера-коды)"
                GetLinkage lineTemp(1), atr, desc
                GetRightPoint RightLine, PointsLeft, PointsRight, CheckBox_EndLine.Value
                DrawPoints PointsRight, CheckLevel(CStr(Num) & " " & "путь правый рельс (точки- номера-коды)", 8).Name, atr
                AddLinkage lineTemp(1), atr, CStr(Num) & " " & "путь правый рельс (точки- номера-коды)"
            Else
                MsgBox "Номер пути не задан"
            End If
    Else
        Response = MsgBox("Необходимо выделить только 2 линии", vbOKOnly)
            If Response = vbOK Then
                Exit Sub
            End If
    End If
End Sub
Function CheckLevel(LevelName As String, i As Integer) As level
    Dim MyLevel As level
    On Error Resume Next
    
    Set CheckLevel = ActiveDesignFile.Levels(LevelName)
    If Err.Number <> 0 And LevelName <> "" Then
         Set MyLevel = ActiveDesignFile.AddNewLevel(LevelName)
         MyLevel.ElementLineWeight = 8
         MyLevel.ElementColor = Int(Rnd * i)
         ActiveDesignFile.Levels.Rewrite
         MsgBox "Создан слой: " & LevelName
         Set CheckLevel = MyLevel
    End If
    Err.Clear
End Function
Function GetNumRail(Atribut As String, index As Integer) As String
    Dim atr() As String
    
    atr = Split(Atribut, "-")
    If UBound(atr) > 0 Then
        GetNumRail = atr(index)
'    Else
'        MsgBox "Неверный формат атрибута"
'        Exit Function
    End If
End Function
Sub GetRightPoint(rLine As LineElement, lPoint() As Point3d, ByRef rPoint() As Point3d, EndHit As Boolean)
    Dim Vector As Vector3d
    Dim Line As LineElement
    Dim i As Long
    Dim j As Long
    Dim pPoint() As Point3d
    ReDim Preserve rPoint(UBound(lPoint))
    
    rPoint(0) = rLine.startPoint
    j = UBound(lPoint) - 1
    If EndHit = True Then
        rPoint(UBound(rPoint)) = rLine.EndPoint
    Else
        j = j + 1
    End If
    
    For i = 1 To j
        If i < j Then
            Vector = Vector3dSubtractPoint3dPoint3d(lPoint(i + 1), lPoint(i))
            Vector = Vector3dUnitPerpendicularXY(Vector)
            Vector = Vector3dScale(Vector, -2)
        Else
            Vector = Vector3dSubtractPoint3dPoint3d(lPoint(i - 1), lPoint(i))
            Vector = Vector3dUnitPerpendicularXY(Vector)
            Vector = Vector3dScale(Vector, 2)
        End If
        Set Line = CreateLineElement2(Nothing, lPoint(i), Point3dAdd(lPoint(i), Point3dFromVector3d(Vector)))
  
        pPoint = rLine.AsIntersectableElement.GetIntersectionPoints(Line, Matrix3dIdentity)
        
        If UBound(pPoint) >= 0 Then
            rPoint(i) = pPoint(0)
        End If
    Next i
End Sub

Sub LineToVertexByStep(mLine As LineElement, ByRef vPoints() As Point3d, HitEnd As Boolean)
    Dim i As Long
    Dim step As Double
    Dim j As Long
    
    step = CDbl(TextBox_Step.Text)
    
    If MultiPage1.SelectedItem.index = 2 Then
        step = GetStepByUch
    End If
        
    i = mLine.Length \ step
        
    If mLine.Length > i * step Then
        ReDim Preserve vPoints(i + 1)
    ElseIf mLine.Length < i * step Then
        i = i - 1
        ReDim Preserve vPoints(i + 1)
    ElseIf mLine.Length < step Then
        MsgBox "Длинна менее шага"
        ReDim Preserve vPoints(1)
    End If
    
        vPoints(0) = mLine.startPoint
    If HitEnd = True Then
        vPoints(UBound(vPoints)) = mLine.EndPoint
    Else
        ReDim Preserve vPoints(UBound(vPoints) - 1)
    End If
        
    For j = 1 To i
        vPoints(j) = mLine.PointAtDistance(step * (j))
    Next j
End Sub

Private Function GetStepByUch() As Long
    Select Case ComboBox_StepByUchastok.ListIndex
        Case 0
            GetStepByUch = 5
        Case 1
            GetStepByUch = 3
        Case 2
            GetStepByUch = 2
    End Select
End Function
Private Sub LineToVertex(mLine As LineElement, ByRef vPoints() As Point3d)
    ReDim Preserve vPoints(mLine.VerticesCount - 1)
    For i = 1 To mLine.VerticesCount
        vPoints(i - 1) = mLine.Vertex(i)
    Next i
End Sub
Sub DrawPoints(Points() As Point3d, LevelName As String, mAtr As String)
    Dim Point As LineElement
    Dim i As Long
    Dim atr As TextElement
    
    For i = 0 To UBound(Points)
        Set Point = CreateLineElement2(Nothing, Points(i), Points(i))
        Point.level = ActiveDesignFile.Levels.Find(LevelName)
        Point.LineWeight = ByLevelLineWeight
        Point.Color = ByLevelColor
        ActiveModelReference.AddElement Point
        Point.Redraw
        AddLinkage Point, mAtr, ""
        If CheckBox_RihtLine.Value = True Then           ' Маркировка рихтовочного рельса
            If GetNumRail(mAtr, 1) <> "H" Then
                MarkerRehtovochLine Points(i), LevelName
            End If
        End If
'        If CheckBox_DrawAtr.Value = True Then
            Set atr = CreateTextElement1(Nothing, mAtr, Points(i), Matrix3dIdentity)
            atr.level = ActiveDesignFile.Levels.Find(LevelName)
            atr.TextStyle.Justification = msdTextJustificationLeftBottom
            atr.TextStyle.Height = CDbl(TextBox_SizeAtr.Text)
            atr.TextStyle.Width = CDbl(TextBox_SizeAtr.Text)
            atr.Color = ByLevelColor
            ActiveModelReference.AddElement atr
            atr.Redraw
'        End If
    Next i
End Sub
Private Sub MarkerRehtovochLine(mPoint As Point3d, LevelName As String)
    Dim Marker As EllipseElement
    
    Set Marker = CreateEllipseElement2(Nothing, mPoint, 1, 1, Matrix3dIdentity)
    Marker.level = ActiveDesignFile.Levels.Find(LevelName)
    Marker.Color = 1
    Marker.LineWeight = 0
    
    ActiveModelReference.AddElement Marker
    Marker.Redraw
End Sub

Private Sub DrawText(iPoint As Point3d, MText As String)
    Dim RotationMatrix As Matrix3d
    Dim mAnno As TextElement
    Dim i As Long
    
    RotationMatrix = Matrix3dFromAxisAndRotationAngle(2, Angle)
    Set mAnno = CreateTextElement1(Nothing, MText, iPoint, RotationMatrix)
    mAnno.TextStyle.Justification = msdTextJustificationLeftBottom
    mAnno.TextStyle.Height = 0.5
    mAnno.TextStyle.Weight = 0.5
    
    ActiveModelReference.AddElement mAnno
    mAnno.Redraw
End Sub
Sub AddLinkage(MyEle As Element, Attribut As String, Description As String)
    Dim Link As String
    DeleteAttributes MyEle
    Link = Attribut & "@" & Description
    AddStringAttribute MyEle, Link
  '  AddStringAttribute MyEle, Description
'    dblk.CopyString Attribut, True
'    dblk.CopyString Description, True
'    MyEle.AddUserAttributeData attrId, dblk
'    MyEle.Rewrite
End Sub
Sub AddStringAttribute(ele As Element, str As String)
    Dim dblk As New DataBlock
    
    dblk.CopyString str, True
    ele.AddUserAttributeData attrId, dblk
    ele.Rewrite
End Sub

Sub DeleteAttributes(ele As Element)
    Dim dblk() As DataBlock
    Dim index As Integer
    
    dblk = ele.GetUserAttributeData(attrId)
    For index = LBound(dblk) To UBound(dblk)
        ele.DeleteUserAttributeData attrId, index
        ele.Rewrite
    Next
End Sub
Sub GetLinkage(MyEle As Element, ByRef Attribut As String, ByRef Description As String)
    Dim dblk() As DataBlock
    Dim Link As String
    Dim Links() As String
    Dim index As Integer
    
        dblk = MyEle.GetUserAttributeData(attrId)
        For index = LBound(dblk) To UBound(dblk)
            dblk(index).Offset = 0
            dblk(index).CopyString Link, False
        Next
    If UBound(dblk) >= 0 Then
        dblk = MyEle.GetUserAttributeData(attrId)
        dblk(0).CopyString Link, False
        Links = Split(Link, "@")
        On Error Resume Next
        Attribut = Links(0)
        Description = Links(1)
    Else
        Attribut = ""
    End If
End Sub

Private Function IsComplanar(Line1 As LineElement, Line2 As LineElement) As Boolean

    If Vector3dDotProductXY(Vector3dSubtractPoint3dPoint3d(Line1.Vertex(2), Line1.Vertex(1)), Line2.Vertex(2), Line2.Vertex(1)) >= 0 Then
        IsComplanar = True
    Else
        IsComplanar = False
    End If
    
End Function
Sub IsLeftRight(ByRef Line1 As LineElement, ByRef Line2 As LineElement)
    Dim Vector As Vector3d
    Dim Line As LineElement
    Dim pPoint() As Point3d
    Dim tempLine As LineElement
    
    Vector = Vector3dSubtractPoint3dPoint3d(Line1.Vertex(3), Line1.Vertex(2))
    Vector = Vector3dUnitPerpendicularXY(Vector)
    Vector = Vector3dScale(Vector, 2)
    
    Set Line = CreateLineElement2(Nothing, Line1.Vertex(2), Point3dAdd(Line1.Vertex(2), Point3dFromVector3d(Vector)))
    pPoint = Line2.AsIntersectableElement.GetIntersectionPoints(Line, Matrix3dIdentity)
    
    If UBound(pPoint) >= 0 Then
        Set tempLine = Line1
        Set Line1 = Line2
        Set Line2 = tempLine
    End If
    
End Sub

Function getEnumeratorCount(oEnumerator As ElementEnumerator) As Long
    Dim count As Long
    With oEnumerator
        .Reset
        Do While .MoveNext
            count = count + 1
        Loop
        .Reset
    End With
    getEnumeratorCount = count
End Function

Function AngleTxt(pSt As Point3d, pEnd As Point3d) As Double
Dim dAng As Double
Dim Angle As Double
Dim ang As Double
Dim dx As Double
Dim dy As Double
dx = pEnd.X - pSt.X
dy = pEnd.Y - pSt.Y
If dy <> 0 Then
    ang = Atn(dx / dy)
    If dx >= 0 And dy > 0 Then
        dAng = ang
    ElseIf dx >= 0 And dy < 0 Then
        dAng = ang + Pi
    ElseIf dx < 0 And dy < 0 Then
        dAng = ang + Pi
    ElseIf dx < 0 And dy > 0 Then
        dAng = ang + 2 * Pi
    End If
ElseIf dy = 0 Then

    If dx > 0 Then
        dAng = Pi / 2
    ElseIf dx < 0 Then
        dAng = 3 * Pi / 4
    End If
End If
Angle = Pi / 2 - dAng

'************* Убрать кавычки для того, что бы автоматом разворачивались подписи
'--------------------------------------------------------------------------
'    If MyForm.CheckBox_rotation.Value = True Then
        If Angle > Pi * 0.5 And Angle < Pi * 1.5 Then Angle = Angle + Pi
        If Angle > -Pi * 1.5 And Angle < -Pi * 0.5 Then Angle = Angle + Pi
'    End If
AngleTxt = Angle

End Function

Private Sub ExportToExcel()
    ' Excel Application, workbook, and sheet object

    Dim xlApp As Excel.Application
    Dim xlBook As Excel.Workbook
    Dim xlSheet As Object
    ' Filename

    Dim fileDoesExist As Boolean
    Dim fileName As String
    
    ' Create Excel Application
    Dim i As Long
    Dim Attribut As String
    Dim Description As String
    Dim rPoints() As Element
    Dim mEnum As ElementEnumerator
    
    Set mEnum = ActiveModelReference.GetSelectedElements
    rPoints = mEnum.BuildArrayFromContents

    Set xlApp = CreateObject("Excel.Application")
    xlApp.Visible = False

    fileName = "CatalogOfSurveyPoints.xlsx"
    fileDoesExist = Dir("d:\" & fileName) > ""
    
 
    Set xlBook = xlApp.Workbooks.Add
    Set xlSheet = xlBook.Sheets(1)
 
    ' Блок для записи ячеек
    
    TablePointsHeader xlSheet ' Формирование шапки таблицы
    
    For i = 0 To UBound(rPoints)
        If rPoints(i).Type = msdElementTypeLine Then
            Dim NumPoint As Long
            NumPoint = i + 1 + 100000 * CDbl(TextBox_BlockNumber.Text)
            xlSheet.Cells(i + 3, 1) = NumPoint
            xlSheet.Cells(i + 3, 2) = rPoints(i).AsLineElement.startPoint.Y
            xlSheet.Cells(i + 3, 3) = rPoints(i).AsLineElement.startPoint.X
            xlSheet.Cells(i + 3, 4) = rPoints(i).AsLineElement.startPoint.Z
            xlSheet.Range(xlSheet.Cells(i + 3, 2), xlSheet.Cells(i + 3, 4)).NumberFormat = "0.000"
            GetLinkage rPoints(i), Attribut, Description
            DrawAttribuWithNumber rPoints(i), NumPoint & "_" & Attribut
            xlSheet.Cells(i + 3, 5) = Attribut
            xlSheet.Cells(i + 3, 6) = Description
            xlSheet.Columns("A:F").AutoFit
        End If
    Next i
   
    Dim index As Integer
    On Error Resume Next
    While Dir(ActiveDesignFile.Path & "\" & "Table_1_" & index & ".xlsx") > ""
        index = index + 1
    Wend
    xlBook.SaveAs fileName:=ActiveDesignFile.Path & "\" & "Table_1_" & index & ".xlsx"
    xlBook.Save
    xlApp.Quit
    MsgBox "Отчет сформирован: " & ActiveDesignFile.Path & "\" & "Table_1_" & index & ".xlsx"
    
End Sub

Private Sub DrawAttribuWithNumber(mElement As Element, mAtr As String)
    Dim MText As TextElement
    
    Set MText = CreateTextElement1(Nothing, mAtr, mElement.AsLineElement.startPoint, Matrix3dIdentity)
    MText.level = mElement.AsLineElement.level
    
    SetTextAtribut MText
    ActiveModelReference.AddElement MText
    MText.Redraw
End Sub

Public Function saveFileAs() As String
    Dim fd As FileDialog, fileName As String
 
    On Error GoTo ErrorHandler
 
    Set fd = Application.FileDialog(msoFileDialogSaveAs)
 
    If fd.Show = True Then
        If fd.SelectedItems(1) <> vbNullString Then
            fileName = fd.SelectedItems(1)
        End If
    Else
        'Stop Code Execution for Null File String
        End
    End If
 
    saveFileAs = fileName
 
    'Cleanup
    Set fd = Nothing
 
    Exit Function
 
ErrorHandler:
    Set fd = Nothing
    MsgBox "Error " & Err & ": " & Error(Err)
 
End Function
Private Sub TablePointsHeader(mSheet As Object)
    mSheet.Cells(1, 1) = "Номер точки"
    mSheet.Cells(1, 2) = "Координаты"
    mSheet.Cells(1, 5) = "Код точки"
    mSheet.Cells(1, 6) = "Примечание"
    mSheet.Range(mSheet.Cells(1, 2), mSheet.Cells(1, 4)).Merge
    mSheet.Range(mSheet.Cells(1, 1), mSheet.Cells(2, 1)).Merge
    mSheet.Range(mSheet.Cells(1, 5), mSheet.Cells(2, 5)).Merge
    mSheet.Range(mSheet.Cells(1, 6), mSheet.Cells(2, 6)).Merge
    mSheet.Cells(2, 2) = "Север"
    mSheet.Cells(2, 3) = "Восток"
    mSheet.Cells(2, 4) = "H"
    mSheet.Range(mSheet.Cells(1, 1), mSheet.Cells(2, 6)).HorizontalAlignment = xlCenter
    mSheet.Columns("A:F").AutoFit
End Sub

Sub PointToRails(mPoint As Point3d, Lines() As Element)
    
End Sub

Sub Project_Point1(mLine As Element, mPoint As Point3d, ByRef ProjPoint As Point3d)

Dim mComplexStr As ElementEnumerator
Dim i As Long
Dim j As Long
Dim minDist As Double
Dim tmpDist As Double
Dim tmpP As Point3d

    Select Case mLine.Type
        Case msdElementTypeLineString
            minDist = 500000
                tmpP = mPoint
                i = mLine.AsLineElement.GetClosestSegment(tmpP)
                tmpP.Z = mLine.AsLineElement.Vertex(i + 1).Z * 0.5 + mLine.AsLineElement.Vertex(i + 2).Z * 0.5

                tmpDist = Dist_Segment_to_Point(mLine.AsLineElement.Vertex(i + 1), mLine.AsLineElement.Vertex(i + 2), tmpP)
                    If tmpDist < minDist Then
                        minDist = tmpDist
                        ProjPoint = Project_Point(mLine.AsLineElement.Vertex(i + 1), mLine.AsLineElement.Vertex(i + 2), tmpP)
                    End If
        Case msdElementTypeComplexString
            Set mComplexStr = mLine.AsComplexStringElement.GetSubElements
                minDist = 5000000
                While mComplexStr.MoveNext
                    Select Case mComplexStr.Current.Type
                        Case msdElementTypeLineString
                            tmpP = mPoint
                            i = mComplexStr.Current.AsLineElement.GetClosestSegment(tmpP)
                            tmpP.Z = mComplexStr.Current.AsLineElement.Vertex(i + 1).Z * 0.5 + mComplexStr.Current.AsLineElement.Vertex(i + 2).Z * 0.5
                            tmpDist = Dist_Segment_to_Point(mComplexStr.Current.AsLineElement.Vertex(i + 1), mComplexStr.Current.AsLineElement.Vertex(i + 2), tmpP)
                                If tmpDist < minDist Then
                                    minDist = tmpDist
                                    ProjPoint = Project_Point(mComplexStr.Current.AsLineElement.Vertex(i + 1), mComplexStr.Current.AsLineElement.Vertex(i + 2), tmpP)
                                End If
                        Case msdElementTypeLine
                            tmpP = mPoint
                            tmpP.Z = mComplexStr.Current.AsLineElement.startPoint.Z
                            tmpDist = Dist_Segment_to_Point(mComplexStr.Current.AsLineElement.startPoint, mComplexStr.Current.AsLineElement.EndPoint, tmpP)
                                If tmpDist < minDist Then
                                minDist = tmpDist
                                ProjPoint = Project_Point(mComplexStr.Current.AsLineElement.startPoint, mComplexStr.Current.AsLineElement.EndPoint, tmpP)
                            End If
                    End Select
                Wend
    End Select
End Sub
Private Function Dist_Segment_to_Point(startPoint As Point3d, EndPoint As Point3d, iPoint As Point3d) As Double
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    Dim tmpL As LineElement
    vPoint = Vector3dSubtractPoint3dPoint3d(iPoint, startPoint)
    vLine = Vector3dSubtractPoint3dPoint3d(EndPoint, startPoint)
    
    c1 = Vector3dDotProduct(vPoint, vLine)
    c2 = Vector3dDotProduct(vLine, vLine)
        If c1 <= 0 Then
            Dist_Segment_to_Point = Point3dDistance(startPoint, iPoint)
        ElseIf c2 <= c1 Then
            Dist_Segment_to_Point = Point3dDistance(EndPoint, iPoint)
        Else
            k = c1 / c2
            vProject = Vector3dScale(vLine, k)
            pProject = Vector3dAdd(Vector3dFromPoint3d(startPoint), vProject)
            Dist_Segment_to_Point = Point3dDistance(Point3dFromVector3d(pProject), iPoint)
        End If
End Function
Private Function Project_Point(startPoint As Point3d, EndPoint As Point3d, iPoint As Point3d) As Point3d
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    
    vPoint = Vector3dSubtractPoint3dPoint3d(iPoint, startPoint)
    vLine = Vector3dSubtractPoint3dPoint3d(EndPoint, startPoint)
    
    c1 = Vector3dDotProduct(vPoint, vLine)
    c2 = Vector3dDotProduct(vLine, vLine)
        If c1 <= 0 Then
            Exit Function
'            Project_Point = startPoint
        ElseIf c2 <= c1 Then
            Exit Function
'            Project_Point = EndPoint
        Else
            k = c1 / c2
            vProject = Vector3dScale(vLine, k)
            Project_Point = Point3dFromVector3d(Vector3dAdd(Vector3dFromPoint3d(startPoint), vProject))
        End If
End Function

Function GetClosestSegment3d(iLine As LineElement, iPoint As Point3d) As Point3d()
    Dim i As Long
    Dim Segment(0 To 1) As Point3d ' 0 - start , 1 - end
    i = iLine.GetClosestVertex(iPoint)
        If i = 0 Then
            Segment(0) = iLine.Vertex(1)
            Segment(1) = iLine.Vertex(2)
        ElseIf i = (iLine.VerticesCount - 1) Then
            Segment(0) = iLine.Vertex((iLine.VerticesCount) - 1)
            Segment(1) = iLine.Vertex(iLine.VerticesCount)
        Else
            i = i + 1
            If Dist_Segment_to_Point(iLine.Vertex(i), iLine.Vertex(i + 1), iPoint) >= Dist_Segment_to_Point(iLine.Vertex(i - 1), iLine.Vertex(i), iPoint) Then
                Segment(0) = iLine.Vertex(i - 1)
                Segment(1) = iLine.Vertex(i)
            Else
                Segment(0) = iLine.Vertex(i)
                Segment(1) = iLine.Vertex(i + 1)
            End If
        End If
    GetClosestSegment3d = Segment
    
End Function

Private Sub ProjectsPoints()
    Dim mEnum As ElementEnumerator
    Dim mLine() As Element
    Dim mPoints() As Element
    Dim i As Long
    Dim j As Long
    Dim prPoint As Point3d
    Dim prPointLine As LineElement
    Dim Attribut As String
    Dim desc As String
    
    Set mEnum = ActiveModelReference.GetSelectedElements
    
    While mEnum.MoveNext
        Select Case mEnum.Current.Type
            Case msdElementTypeLine
                RedimPreserve mPoints
                Set mPoints(UBound(mPoints)) = mEnum.Current
            Case msdElementTypeLineString
                RedimPreserve mLine
                Set mLine(UBound(mLine)) = mEnum.Current
            Case msdElementTypeComplexString
                RedimPreserve mLine
                Set mLine(UBound(mLine)) = mEnum.Current
        End Select
    Wend
    If UBound(mLine) < 0 Or UBound(mPoints) < 0 Then
        MsgBox "Не выделены объекты"
        Exit Sub
    End If
    Dim tpmPont As Point3d
    For i = 0 To UBound(mPoints)
        For j = 0 To UBound(mLine)
            Project_Point1 mLine(j), mPoints(i).AsLineElement.startPoint, prPoint
            If Not Point3dEqual(tpmPont, prPoint) Then
                GetLinkage mLine(j), Attribut, desc
                Set prPointLine = CreateLineElement2(Nothing, prPoint, prPoint)
                prPointLine.level = ActiveDesignFile.Levels.Find(desc)
                prPointLine.LineWeight = ByLevelLineWeight
                prPointLine.Color = ByLevelColor
                ActiveModelReference.AddElement prPointLine
                prPointLine.Redraw
    '            GetLinkage mLine(j), Attribut, Desc
                AddLinkage prPointLine, Attribut, ""
            End If
        Next j
    Next i

End Sub

Sub RedimPreserve(ByRef mB() As Element)
    Dim i As Long
    On Error Resume Next
    i = UBound(mB) + 1
    If Err.Number = 9 Then
        ReDim mB(0)
    Else: ReDim Preserve mB(i)
    End If
    Err.Clear
End Sub

Private Sub SearchNotAtribut()
    Dim mEnum As ElementEnumerator
    Dim Marker() As Point3d
    Dim atr As String, Des As String
    
    
    Set mEnum = ActiveModelReference.GetSelectedElements
    
    While mEnum.MoveNext
        Select Case mEnum.Current
            Case msdElementTypeLine
            GetLinkage mEnum.Current, atr, desc
        End Select
    Wend
    
End Sub

Private Sub DrawAttr()

Dim mEnum As ElementEnumerator
Dim mAtr As String
Dim mDesc As String
Dim i As Long 'Общее количество объектов
Dim j As Long 'Количество без атрибутов

Dim MText As TextElement

Set mEnum = ActiveModelReference.GetSelectedElements

While mEnum.MoveNext
    If mEnum.Current.Type = msdElementTypeLine Then
        i = i + 1
        GetLinkage mEnum.Current, mAtr, mDesc
        If mAtr <> "" Then
            Set MText = CreateTextElement1(Nothing, mAtr, mEnum.Current.AsLineElement.startPoint, Matrix3dIdentity)
            MText.level = mEnum.Current.AsLineElement.level
            
            SetTextAtribut MText
            ActiveModelReference.AddElement MText
            MText.Redraw
        Else
            j = j + 1
            AddMarkerNoAtr mEnum.Current.AsLineElement.startPoint
        End If
    End If
Wend
    
    MsgBox "Общее количество точке: " & i & Chr(10) & "Без атрибутов: " & j
End Sub
Private Sub AddMarkerNoAtr(mPoint As Point3d)
    Dim mMarker As EllipseElement
    
    Set mMarker = CreateEllipseElement2(Nothing, mPoint, 2, 2, Matrix3dIdentity)
    mMarker.level = CheckLevelMarker("_!_MarkerNoAtribut_!_")
    mMarker.Color = ByLevelColor
    mMarker.LineWeight = ByLevelLineWeight
    ActiveModelReference.AddElement mMarker
    mMarker.Redraw
    
End Sub
Function CheckLevelMarker(LevelName As String) As level
    Dim MyLevel As level
    On Error Resume Next
    
    Set CheckLevelMarker = ActiveDesignFile.Levels(LevelName)
    If Err.Number <> 0 And LevelName <> "" Then
         Set MyLevel = ActiveDesignFile.AddNewLevel(LevelName)
         MyLevel.ElementLineWeight = 2
         MyLevel.ElementColor = 3
         ActiveDesignFile.Levels.Rewrite
         MsgBox "Создан слой: " & LevelName
         Set CheckLevelMarker = MyLevel
    End If
    Err.Clear
End Function
Private Sub SetTextAtribut(ByRef MText As TextElement)
    MText.TextStyle.Justification = msdTextJustificationLeftBottom
    MText.TextStyle.Height = CDbl(TextBox_SizeAtr.Text)
    MText.TextStyle.Width = CDbl(TextBox_SizeAtr.Text)
    MText.TextStyle.Font = ActiveDesignFile.Fonts("Arial")
    MText.Color = ByLevelColor
    
End Sub

Private Sub CommandButtonCutLines_Click()
    CommandState.StartLocate New LCE_CutLines
End Sub



Private Sub SpinButton1_Change()
    With SpinButton1
    .Min = 0
    .Max = 200
    .SmallChange = 1
    .ControlTipText = "Добавление номера в конце"
    End With
    If SpinButton1.Value > 0 Then
        TextBox_Number.Text = CStr(SpinButton1.Value)
    Else
        TextBox_Number.Text = ""
    End If
End Sub

Private Sub SpinButton2_Change()
    With SpinButton2
    
    .Min = 0
    .Max = 10000
    .SmallChange = 1
    End With
    
    If SpinButton2.Value > 0 Then
        TextBox_DopuskCurve.Text = CStr(SpinButton2.Value / 100)
    Else
        TextBox_DopuskCurve.Text = "0.00"
    End If
End Sub

Private Sub TextBox_Number_Change()
    Dim atr As String
    atr = TextBox_Attribut.Text
    TextBox_Attribut.Text = GetNumRail(atr, 0) & "-" & GetNumRail(atr, 1) & "-" & GetNumRail(ComboBox_Code.Text, 0) & TextBox_Number.Text
    
End Sub

Private Sub UserForm_Initialize()
    MultiPage1.Value = 0
    InizialazeCodes
    InizialazeStep
End Sub
