Attribute VB_Name = "Module1"
Option Explicit
Public imlLine() As String
Public PathIML As String
Declare Function mdlDialog_fileOpen Lib "stdmdlbltin.dll" (ByVal _
    fileName As String, ByVal rFileH As Long, ByVal _
    resourceId As Long, ByVal suggestedFileName As String, _
    ByVal filterString As String, ByVal defaultDirectory As String, _
    ByVal titleString As String) As Long
Sub Main()
    UserForm1.Show vbModeless
End Sub

Attribute VB_Name = "UserForm1"
Attribute VB_Base = "0{16EC9399-60CA-4E93-B1A3-70E80554D8A0}{4C5A3BBA-342D-4A55-B138-3B2C6E1F34B8}"
Attribute VB_GlobalNameSpace = False
Attribute VB_Creatable = False
Attribute VB_PredeclaredId = True
Attribute VB_Exposed = False
Attribute VB_TemplateDerived = False
Attribute VB_Customizable = False
Option Explicit

Private Sub OpenIML()
    Dim strFName As String
    Dim lngfhandle As Long
    Dim lngrid As Long
    Dim retVal As Long
    Dim FFile As Long
    ReDim imlLine(0)
    
    strFName = Space(255)
    retVal = mdlDialog_fileOpen(strFName, lngfhandle, lngrid, "", "*.iml", _
                                    ActiveDesignFile.Path, "Открыть файл IML")
    Select Case retVal
        Case 0 'Open
            PathIML = Left(strFName, InStr(1, strFName, Chr(0)) - 1)
            FFile = FreeFile
            Open PathIML For Input As #FFile
                While EOF(FFile) = False
                    Line Input #FFile, imlLine(UBound(imlLine))
                    ReDim Preserve imlLine(UBound(imlLine) + 1)
                Wend
                ReDim Preserve imlLine(UBound(imlLine) - 1)
            MsgBox "Файл IML загружен:" & vbCr & strFName
        Case 1 'Cancel
            MsgBox "Файл не выделен"
    End Select
End Sub
Private Sub GetRegion()
    Dim Element As ShapeElement
    Dim MyEnum As ElementEnumerator
    Dim mRegions() As Element
    Dim i As Long
    Dim j As Long
    Dim k As Long
    Dim sXYZ() As String
    Dim aRegion() As Point3d
    Dim mPoint As Point3d
    Dim OutIML() As String
    Dim fName() As String
    
    ReDim OutIML(0)
    ReDim fName(0)
    OutIML(0) = imlLine(0)
    ReDim Preserve OutIML(1)
    
    Set MyEnum = ActiveModelReference.GetSelectedElements
    mRegions = MyEnum.BuildArrayFromContents
    If UBound(mRegions) < 0 Then MsgBox "Регионы не выделены"
        For j = 0 To UBound(mRegions)
            If mRegions(j).Type = msdElementTypeShape Then
                aRegion = mRegions(j).AsShapeElement.GetVertices
                    For i = 3 To (UBound(imlLine) - 6) Step 9
                        sXYZ = Split(Mid(imlLine(i), 5), " ")
                        mPoint.X = sXYZ(0)
                        mPoint.Y = sXYZ(1)
                       ' mPoint.Z = sXYZ(2)
                            If Point3dInPolygonXY(mPoint, aRegion) >= 0 Then
                                For k = 1 To 10
                                On Error Resume Next
                                    OutIML(UBound(OutIML)) = imlLine((i - 3) + k)
                                    ReDim Preserve OutIML(UBound(OutIML) + 1)
                                        If k = 1 Then
                                            fName(UBound(fName)) = Split(imlLine(i - 2), "=")(1) & ".jpg"
                                            ReDim Preserve fName(UBound(fName) + 1)
                                        End If
                                Next k
                                ReDim Preserve OutIML(UBound(OutIML) - 1)
                                
                            End If
                    Next i
                    If UBound(OutIML) <= 1 Then
                    MsgBox "не вошло"
                    Else
                    ReDim Preserve fName(UBound(fName) - 1)
                    OutSaveIML OutIML, (j + 1), ".iml"
                    OutSaveIML fName, (j + 1), ".txt"
                    End If
            Else
               Call MsgBox("Выбран не шейп - IML не будет сформирован")
            End If
            ReDim Preserve OutIML(1)
        Next j
End Sub

Private Sub OutSaveIML(oString() As String, id As Long, exe As String)
    Dim PathSave As String
    Dim FFile As Long
    Dim i As Long
    
    PathSave = Left(PathIML, InStr(1, PathIML, ".iml") - 1) & "_split_" & id & exe
    FFile = FreeFile
    
    Open PathSave For Output As #FFile
        For i = 0 To UBound(oString)
            Print #FFile, oString(i)
        Next i
    Close #FFile
    
End Sub
Private Sub CommandButton_openIML_Click()
    OpenIML
End Sub

Private Sub CommandButton_splitIML_Click()
    GetRegion
End Sub
