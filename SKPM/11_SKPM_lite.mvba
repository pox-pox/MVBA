Attribute VB_Name = "Module1"
Option Explicit
Public myExcel As New Excel.Application
Public myWorkbook As Excel.Workbook
Public CurrSheet As Worksheet
Public A As Double 'Сторона треугольника
Public H As Double 'Высота треугольника
Public B As Double 'Ширина треугольника
Public D As Double 'Диаметр
Public Radius As Double
Public oLevel As String

Declare Function mdlDialog_fileOpen Lib "stdmdlbltin.dll" (ByVal _
    fileName As String, ByVal rFileH As Long, ByVal _
    resourceId As Long, ByVal suggestedFileName As String, _
    ByVal filterString As String, ByVal defaultDirectory As String, _
    ByVal titleString As String) As Long
Public PathXls As String
Sub LoadSett()
    Dim strFName As String
    Dim lngfhandle As Long
    Dim lngrid As Long
    Dim retVal As Long
    strFName = Space(255)
    retVal = mdlDialog_fileOpen(strFName, lngfhandle, lngrid, "", "*.xls", _
                                    ActiveDesignFile.Path, "Открыть файл настроек")
    Select Case retVal
        Case 0 'Open
            PathXls = Left(strFName, InStr(1, strFName, Chr(0)) - 1)
            MsgBox "Загружены настройки из файла:" & vbCr & strFName
            Set myWorkbook = myExcel.Workbooks.Open(PathXls)
            Set myExcel = Nothing
            myExcel.Quit
            Module1.innitialization
        Case 1 'Cancel
            MsgBox "Файл не выделен"
    End Select
End Sub
Sub Main()
    MyForm.Show vbModeless
End Sub
Private Sub innitialization()
    Dim curRow As Long
    Dim i As Long
    Dim bool As Boolean
    curRow = 2 ' Начинать поиск со сторой строки
    Set CurrSheet = myWorkbook.Worksheets(1)
    While CurrSheet.Cells(curRow, 2) <> ""
        If bool = False Then
            MyForm.lbTypeZnak.AddItem CurrSheet.Cells(curRow, 2)
            bool = True
        End If
        For i = 0 To MyForm.lbTypeZnak.ListCount - 1
            If MyForm.lbTypeZnak.List(i) = CurrSheet.Cells(curRow, 2) Then
                Exit For
            End If
            If i = MyForm.lbTypeZnak.ListCount - 1 Then MyForm.lbTypeZnak.AddItem CurrSheet.Cells(curRow, 2)
        Next i
    curRow = curRow + 1
    Wend
End Sub
Sub IniSize(Znak As String)
    Dim curRow As Long
    curRow = 2
    Set CurrSheet = myWorkbook.Worksheets(1)
    MyForm.lbSaze.Clear
    While CurrSheet.Cells(curRow, 2) <> ""
        If CurrSheet.Cells(curRow, 2) = Znak Then
            If CurrSheet.Cells(curRow, 3) <> "" Then
                MyForm.lbSaze.AddItem CurrSheet.Cells(curRow, 3)
            Else:
                Module1.Draw MyForm.lbTypeZnak, ""
            End If
        End If
        curRow = curRow + 1
    Wend
End Sub
Sub Draw(ZnakType As String, SizeZ As String)
    Dim curRow As Long
    Dim myPolyTest As New PCE_PolyTest
    Dim DrawMetod As String ' Метод нанесения
    curRow = 2
    Do While CurrSheet.Cells(curRow, 2) <> ""
        If CurrSheet.Cells(curRow, 2) & CurrSheet.Cells(curRow, 3) = ZnakType & SizeZ Then
            DrawMetod = CurrSheet.Cells(curRow, 1)
            oLevel = CurrSheet.Cells(curRow, 8)
            Exit Do
        End If
        curRow = curRow + 1
    Loop
    Select Case DrawMetod
        Case "TREUG"
            A = CDbl(CurrSheet.Cells(curRow, 4)) * 0.001
            Radius = A * 0.5 / Cos(Radians(30))
            PCE_DrawPoly (3)
        Case "STOP"
            B = CDbl(CurrSheet.Cells(curRow, 6)) * 0.001
            Radius = B * 0.5 / Cos(Radians(22.5))
            PCE_DrawPoly (8)
        Case "KVADR"
            B = CDbl(CurrSheet.Cells(curRow, 6)) * 0.001
            Radius = B * 0.5 / Cos(Radians(45))
            PCE_DrawPoly (4)
        Case "KRUG"
            D = CDbl(CurrSheet.Cells(curRow, 7)) * 0.001
            Radius = D * 0.5
            CommandState.StartPrimitive New PCE_Circle, True
        Case "PRUG"
            H = CDbl(CurrSheet.Cells(curRow, 5)) * 0.001
            B = CDbl(CurrSheet.Cells(curRow, 6)) * 0.001
            CommandState.StartPrimitive New PCE_Prug, True
        Case "POINT"
            CommandState.StartPrimitive New PCE_Point, True
        Case "LINE"
            CommandState.StartPrimitive New PCE_Line, True
    End Select
    
End Sub

Private Sub PCE_DrawPoly(edges As Integer)
    Dim myPolyTest As New PCE_PolyTest
    myPolyTest.Verticies = edges
    CommandState.StartPrimitive myPolyTest
End Sub
Sub CheckLevel(Element As Element) ' Проверка файла на наличие слоя, если нет, то создает
    Dim CheckLevel As Level
    On Error Resume Next
    Set CheckLevel = ActiveDesignFile.Levels(oLevel)
    If Err.Number <> 0 Then
        Set CheckLevel = ActiveDesignFile.AddNewLevel(oLevel)
    End If
    Err.Clear
    Element.Level = CheckLevel
End Sub

Function RotateEl(dView As View, bPoint As Point3d, dPoint As Point3d) As Transform3d
    Dim DynRot As Matrix3d
    Dim prPoint As Point3d 'Проекция направляющей точки на плоскость XY
    Dim DirectVector As Point3d
    Dim ProectDV As Point3d
    
        prPoint = dPoint
        prPoint.Z = bPoint.Z
        
        If dView.Index = 1 Then
            prPoint.Y = bPoint.Y
        End If
        
        DirectVector.X = dPoint.X - bPoint.X
        DirectVector.Y = dPoint.Y - bPoint.Y
        DirectVector.Z = dPoint.Z - bPoint.Z
        ProectDV.X = prPoint.X - bPoint.X
        ProectDV.Y = prPoint.Y - bPoint.Y
        ProectDV.Z = prPoint.Z - bPoint.Z
        
        DynRot = Matrix3dFromRotationBetweenVectors(ProectDV, DirectVector)
        RotateEl = Transform3dFromMatrix3dAndFixedPoint3d(DynRot, bPoint)
End Function
Sub ReplaceCell(name As String)
    Dim myFilter As New ElementScanCriteria
    Dim myAttach As Attachment
    Dim myEnum As ElementEnumerator
    Dim mySCell As SharedCellElement
    Dim rotation As Matrix3d
    Dim transform As Transform3d
    Dim myCircle As EllipseElement
    Dim MyPoint As LineElement ' точка
    Dim R As Double ' Радиус окружности
    Dim H As Double
    Dim B As Double
    Dim i As Long
    Dim compareCellName As String
    Dim Prug(0 To 3) As Point3d
    Dim MyPrug As ShapeElement
    Set myAttach = ActiveDesignFile.DefaultModelReference.Attachments(MyForm.cmbReference.ListIndex + 1)
    
        If InStr(1, name, "*", vbTextCompare) > 0 Then
            i = InStr(1, name, "*", vbTextCompare)
            name = Left(name, i - 1)
        End If

    
    myFilter.ExcludeAllTypes
    myFilter.IncludeType msdElementTypeSharedCell
    
    Set myEnum = myAttach.Scan(myFilter)
        While myEnum.MoveNext
            Select Case myEnum.Current.Type
                Case msdElementTypeSharedCell
                    Set mySCell = myEnum.Current
                            If i > 0 Then
                                compareCellName = Left(mySCell.name, i - 1)
                            Else: compareCellName = mySCell.name
                            End If
                        If compareCellName = name Then
                            Select Case MyForm.cmbPrimitiv.Text
                                Case "Окружность"
                                    R = CDbl(MyForm.tbRadius.Text)
                                    Set myCircle = CreateEllipseElement2(Nothing, mySCell.Origin, R, R, Matrix3dIdentity)
                                    ActiveModelReference.AddElement myCircle
                                    myCircle.Redraw
                                Case "Прямоугольник"
                                    H = CDbl(MyForm.tbH.Text)
                                    B = CDbl(MyForm.tbB.Text)
                                    rotation = mySCell.rotation
                                    transform = Transform3dFromMatrix3dAndFixedPoint3d(rotation, mySCell.Origin)
                                    Prug(0).X = mySCell.Origin.X - B * 0.5
                                    Prug(0).Y = mySCell.Origin.Y - H * 0.5
                                    Prug(0).Z = mySCell.Origin.Z
                                    Prug(1).X = mySCell.Origin.X - B * 0.5
                                    Prug(1).Y = mySCell.Origin.Y + H * 0.5
                                    Prug(1).Z = mySCell.Origin.Z
                                    Prug(2).X = mySCell.Origin.X + B * 0.5
                                    Prug(2).Y = mySCell.Origin.Y + H * 0.5
                                    Prug(2).Z = mySCell.Origin.Z
                                    Prug(3).X = mySCell.Origin.X + B * 0.5
                                    Prug(3).Y = mySCell.Origin.Y - H * 0.5
                                    Prug(3).Z = mySCell.Origin.Z
                                    Set MyPrug = CreateShapeElement1(Nothing, Prug)
                                    MyPrug.transform transform
                                    ActiveModelReference.AddElement MyPrug
                                    MyPrug.Redraw
                                Case "Точка"
                                    Set MyPoint = CreateLineElement2(Nothing, mySCell.Origin, mySCell.Origin)
                                    ActiveModelReference.AddElement MyPoint
                                    MyPoint.Redraw
                            End Select
                        End If
            End Select
        Wend
End Sub

Attribute VB_Name = "MyForm"
Attribute VB_Base = "0{35963084-A6B0-414C-9764-49ADC3683E91}{BEB93C10-A995-4FD4-B3BB-A6C4CCED645F}"
Attribute VB_GlobalNameSpace = False
Attribute VB_Creatable = False
Attribute VB_PredeclaredId = True
Attribute VB_Exposed = False
Attribute VB_TemplateDerived = False
Attribute VB_Customizable = False
Option Explicit

Private Sub bChange_Click()
    Module1.ReplaceCell cbCell.Text
End Sub

Private Sub cbLoad_Click()
    Module1.LoadSett
End Sub


Private Sub cmbPrimitiv_Change()
Select Case MyForm.cmbPrimitiv.Text
    Case "Окружность"
        fRadius.Visible = True
        fBH.Visible = False
    Case "Прямоугольник"
        fRadius.Visible = False
        fBH.Visible = True
    Case "Точка"
        fBH.Visible = False
        fRadius.Visible = False
End Select

End Sub

Private Sub lbSaze_DblClick(ByVal Cancel As MSForms.ReturnBoolean)
    Module1.Draw lbTypeZnak, lbSaze
End Sub

Private Sub lbTypeZnak_Change()
    Module1.IniSize (lbTypeZnak)
End Sub

Private Sub UserForm_Initialize()
Dim myLevel As Level
Dim MyModel As ModelReference
Dim myAttachment As Attachment
Set MyModel = ActiveDesignFile.DefaultModelReference
    For Each myAttachment In MyModel.Attachments
        Debug.Print myAttachment.AttachName
        cmbReference.AddItem myAttachment.AttachName
        Debug.Print "ListIndex = " & cmbReference.ListIndex
        Debug.Print myAttachment.name
        myAttachment.LogicalName = myAttachment.AttachName
    Next

cmbPrimitiv.AddItem "Окружность"
cmbPrimitiv.AddItem "Прямоугольник"
cmbPrimitiv.AddItem "Точка"
End Sub

Attribute VB_Name = "PCE_Circle"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IPrimitiveCommandEvents
Dim pt3BasePoint As Point3d

Private Sub IPrimitiveCommandEvents_Cleanup()

End Sub

Private Sub IPrimitiveCommandEvents_DataPoint(Point As Point3d, ByVal View As View)
    Dim myCircle As EllipseElement
    Dim rotation As Matrix3d
    Dim transform As Transform3d
    rotation = Matrix3dInverse(View.rotation)
    transform = Transform3dFromMatrix3dAndFixedPoint3d(rotation, Point)
    Set myCircle = CreateEllipseElement2(Nothing, Point, Radius, Radius, Matrix3dIdentity)
    myCircle.transform transform
    Module1.CheckLevel myCircle
    ActiveModelReference.AddElement myCircle
    myCircle.Redraw
End Sub

Private Sub IPrimitiveCommandEvents_Dynamics(Point As Point3d, ByVal View As View, ByVal DrawMode As MsdDrawingMode)
    Dim myCircle As EllipseElement
    Dim rotation As Matrix3d
    Dim transform As Transform3d
    rotation = Matrix3dInverse(View.rotation)
    transform = Transform3dFromMatrix3dAndFixedPoint3d(rotation, Point)
    Set myCircle = CreateEllipseElement2(Nothing, Point, Radius, Radius, Matrix3dIdentity)
    myCircle.transform transform
    myCircle.Redraw DrawMode
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
    CommandState.StartDynamics
    
End Sub

Attribute VB_Name = "PCE_Line"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IPrimitiveCommandEvents
Dim bool As Boolean
Dim bPoint As Point3d

Private Sub IPrimitiveCommandEvents_Cleanup()

End Sub

Private Sub IPrimitiveCommandEvents_DataPoint(Point As Point3d, ByVal View As View)
Dim MyLine As LineElement
    If bool = False Then
        bPoint = Point
        CommandState.StartDynamics
        bool = True
    ElseIf bool = True Then
        Set MyLine = CreateLineElement2(Nothing, bPoint, Point)
        Module1.CheckLevel MyLine
        ActiveModelReference.AddElement MyLine
        MyLine.Redraw
        bool = False
        CommandState.StopDynamics
    End If
End Sub

Private Sub IPrimitiveCommandEvents_Dynamics(Point As Point3d, ByVal View As View, ByVal DrawMode As MsdDrawingMode)
    Dim MyLine As LineElement
    Set MyLine = CreateLineElement2(Nothing, bPoint, Point)
    MyLine.Redraw DrawMode
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
End Sub

Attribute VB_Name = "PCE_Point"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IPrimitiveCommandEvents

Private Sub IPrimitiveCommandEvents_Cleanup()

End Sub

Private Sub IPrimitiveCommandEvents_DataPoint(Point As Point3d, ByVal View As View)
    Dim MyLine As LineElement
    Set MyLine = CreateLineElement2(Nothing, Point, Point)
    Module1.CheckLevel MyLine
    ActiveModelReference.AddElement MyLine
    MyLine.Redraw
End Sub

Private Sub IPrimitiveCommandEvents_Dynamics(Point As Point3d, ByVal View As View, ByVal DrawMode As MsdDrawingMode)
    Dim MyLine As LineElement
    Set MyLine = CreateLineElement2(Nothing, Point, Point)
    MyLine.Redraw DrawMode
End Sub

Private Sub IPrimitiveCommandEvents_Keyin(ByVal Keyin As String)
    
End Sub

Private Sub IPrimitiveCommandEvents_Reset()
    CommandState.StartDefaultCommand
End Sub

Private Sub IPrimitiveCommandEvents_Start()
    CommandState.EnableAccuSnap
    CommandState.StartDynamics
End Sub

Attribute VB_Name = "PCE_PolyTest"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents
Public Verticies As Long
Dim dAngle As Double
Dim bool As Boolean
Dim BasPoint As Point3d


Private Sub IPrimitiveCommandEvents_Cleanup()

End Sub

Private Sub IPrimitiveCommandEvents_DataPoint(Point As Point3d, ByVal View As View)
    Dim pt3PolyPoints() As Point3d
    ReDim pt3PolyPoints(0 To Verticies - 1) As Point3d
    Dim myShapeElem As ShapeElement
    Dim i As Long
    Dim rotation As Matrix3d
    Dim transform As Transform3d

    rotation = Matrix3dInverse(View.rotation)
    
    If MyForm.cbFreeRot.Value = False Then
        BasPoint = Point
        bool = True
    End If
    
    If bool = False Then
        BasPoint = Point
        bool = True
    ElseIf bool = True Then
        transform = Transform3dFromMatrix3dAndFixedPoint3d(rotation, BasPoint)
        For i = 0 To Verticies - 1
                pt3PolyPoints(i) = Point3dAddAngleDistance(BasPoint, Radians(360 / Verticies * i) + dAngle, Radius, 0)
        Next i
        Set myShapeElem = CreateShapeElement1(Nothing, pt3PolyPoints)
        myShapeElem.transform transform
            If MyForm.cbFreeRot.Value = True Then
                myShapeElem.transform Module1.RotateEl(View, BasPoint, Point)
            End If
        Module1.CheckLevel myShapeElem
        ActiveModelReference.AddElement myShapeElem
        myShapeElem.Redraw
        bool = False
    End If
End Sub

Private Sub IPrimitiveCommandEvents_Dynamics(Point As Point3d, ByVal View As View, ByVal DrawMode As MsdDrawingMode)
    Dim pt3PolyPoints() As Point3d
    ReDim pt3PolyPoints(0 To Verticies - 1) As Point3d
    Dim myShapeElem As ShapeElement
    Dim i As Long
    Dim rotation As Matrix3d
    Dim transform As Transform3d
    Dim dynAngle As Double
    rotation = Matrix3dInverse(View.rotation)
    
    If bool = False Then
        transform = Transform3dFromMatrix3dAndFixedPoint3d(rotation, Point)
        For i = 0 To Verticies - 1
            pt3PolyPoints(i) = Point3dAddAngleDistance(Point, Radians(360 / Verticies * i) + dAngle, Radius, 0)
        Next i
        Set myShapeElem = CreateShapeElement1(Nothing, pt3PolyPoints)
        myShapeElem.transform transform
        myShapeElem.Redraw DrawMode
    ElseIf bool = True Then
        transform = Transform3dFromMatrix3dAndFixedPoint3d(rotation, BasPoint)
        For i = 0 To Verticies - 1
            pt3PolyPoints(i) = Point3dAddAngleDistance(BasPoint, Radians(360 / Verticies * i) + dAngle, Radius, 0)
        Next i
        Set myShapeElem = CreateShapeElement1(Nothing, pt3PolyPoints)
        myShapeElem.transform transform
            If MyForm.cbFreeRot.Value = True Then
                myShapeElem.transform Module1.RotateEl(View, BasPoint, Point)
            End If
        myShapeElem.Redraw DrawMode
    End If
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
    Select Case Verticies
        Case 3
            dAngle = Radians(-30)
            If MyForm.cb45.Value = True Then dAngle = dAngle - Pi
        Case 4
            dAngle = Radians(-45)
            If MyForm.cb45.Value = True Then dAngle = 0
        Case 8
            dAngle = Radians(-22.5)
    End Select
    CommandState.StartDynamics
End Sub

Attribute VB_Name = "PCE_Prug"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Dim bool As Boolean
Dim BasPoint As Point3d

Implements IPrimitiveCommandEvents

Private Sub IPrimitiveCommandEvents_Cleanup()

End Sub

Private Sub IPrimitiveCommandEvents_DataPoint(Point As Point3d, ByVal View As View)
Dim Prug(0 To 3) As Point3d
Dim MyPrug As ShapeElement
Dim rotation As Matrix3d
Dim transform As Transform3d

    If MyForm.cbFreeRot.Value = False Then
        BasPoint = Point
        bool = True
    End If
    
    If bool = False Then
        BasPoint = Point
        bool = True
    ElseIf bool = True Then
        rotation = Matrix3dInverse(View.rotation)
        transform = Transform3dFromMatrix3dAndFixedPoint3d(rotation, BasPoint)
        Prug(0).X = BasPoint.X - B * 0.5
        Prug(0).Y = BasPoint.Y - H * 0.5
        Prug(0).Z = BasPoint.Z
        Prug(1).X = BasPoint.X - B * 0.5
        Prug(1).Y = BasPoint.Y + H * 0.5
        Prug(1).Z = BasPoint.Z
        Prug(2).X = BasPoint.X + B * 0.5
        Prug(2).Y = BasPoint.Y + H * 0.5
        Prug(2).Z = BasPoint.Z
        Prug(3).X = BasPoint.X + B * 0.5
        Prug(3).Y = BasPoint.Y - H * 0.5
        Prug(3).Z = BasPoint.Z
        Set MyPrug = CreateShapeElement1(Nothing, Prug)
        MyPrug.transform transform
            If MyForm.cbFreeRot.Value = True Then
                MyPrug.transform Module1.RotateEl(View, BasPoint, Point)
            End If
        Module1.CheckLevel MyPrug
        ActiveModelReference.AddElement MyPrug
        MyPrug.Redraw
    bool = False
    End If
End Sub

Private Sub IPrimitiveCommandEvents_Dynamics(Point As Point3d, ByVal View As View, ByVal DrawMode As MsdDrawingMode)
Dim Prug(0 To 3) As Point3d
Dim MyPrug As ShapeElement
Dim rotation As Matrix3d
Dim transform As Transform3d
rotation = Matrix3dInverse(View.rotation)

    If bool = False Then
        transform = Transform3dFromMatrix3dAndFixedPoint3d(rotation, Point)
        Prug(0).X = Point.X - B * 0.5
        Prug(0).Y = Point.Y - H * 0.5
        Prug(0).Z = Point.Z
        Prug(1).X = Point.X - B * 0.5
        Prug(1).Y = Point.Y + H * 0.5
        Prug(1).Z = Point.Z
        Prug(2).X = Point.X + B * 0.5
        Prug(2).Y = Point.Y + H * 0.5
        Prug(2).Z = Point.Z
        Prug(3).X = Point.X + B * 0.5
        Prug(3).Y = Point.Y - H * 0.5
        Prug(3).Z = Point.Z
        Set MyPrug = CreateShapeElement1(Nothing, Prug)
        MyPrug.transform transform
        MyPrug.Redraw DrawMode

    ElseIf bool = True Then

        transform = Transform3dFromMatrix3dAndFixedPoint3d(rotation, BasPoint)
        Prug(0).X = BasPoint.X - B * 0.5
        Prug(0).Y = BasPoint.Y - H * 0.5
        Prug(0).Z = BasPoint.Z
        Prug(1).X = BasPoint.X - B * 0.5
        Prug(1).Y = BasPoint.Y + H * 0.5
        Prug(1).Z = BasPoint.Z
        Prug(2).X = BasPoint.X + B * 0.5
        Prug(2).Y = BasPoint.Y + H * 0.5
        Prug(2).Z = BasPoint.Z
        Prug(3).X = BasPoint.X + B * 0.5
        Prug(3).Y = BasPoint.Y - H * 0.5
        Prug(3).Z = BasPoint.Z
        Set MyPrug = CreateShapeElement1(Nothing, Prug)
        MyPrug.transform transform
            If MyForm.cbFreeRot.Value = True Then
                MyPrug.transform Module1.RotateEl(View, BasPoint, Point)
            End If
        MyPrug.Redraw DrawMode
    End If
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
    CommandState.StartDynamics
End Sub
