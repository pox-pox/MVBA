Attribute VB_Name = "Module1"
Option Explicit
Public tHeight As TextElement
Public dLine As LineElement
Public tDiametr As TextElement
Public tDist As TextElement
Public mCell1 As CellElement
Public mCell2 As CellElement
Public tCharct1 As TextElement
Public tCharct2 As TextElement

Sub Main()
    UserForm1.Show vbModeless
End Sub

Attribute VB_Name = "PCE_PlaceCharacteristic"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private saveJast As TextStyle


Implements IPrimitiveCommandEvents

Private Sub IPrimitiveCommandEvents_Cleanup()

End Sub

Private Sub IPrimitiveCommandEvents_DataPoint(Point As Point3d, ByVal View As View)
    AddElementToModel tHeight
    AddElementToModel dLine
    AddElementToModel tDiametr
    AddElementToModel tDist
    AddElementToModel mCell1
    AddElementToModel tCharct1
    AddElementToModel tCharct2
End Sub

Private Sub IPrimitiveCommandEvents_Dynamics(Point As Point3d, ByVal View As View, ByVal DrawMode As MsdDrawingMode)
    Dim tHRange As Range3d
    Dim tDRange As Range3d
    Dim tDistRange As Range3d
    Dim CellRange1 As Range3d
    Dim CellGabaritX As Double
    Dim Charct1Range As Range3d
    Dim Charct2Range As Range3d
    Dim CharctMaxRangeX As Double
    Dim vOffset As Double
    
    vOffset = CDbl(UserForm1.TextBox_TextInterval.Text)
    
    Set tHeight = CreateTextElement1(Nothing, UserForm1.TextBox_cHeight.Text, Point, Matrix3dIdentity)
    Set tDiametr = CreateTextElement1(Nothing, UserForm1.TextBox_cDiametr.Text, Point, Matrix3dIdentity)
    Set tDist = CreateTextElement1(Nothing, UserForm1.TextBox_cDist.Text, Point, Matrix3dIdentity)
    Set mCell1 = CreateCellElement3(UserForm1.ComboBox_CellName1.Text, Point, True)
    Set tCharct1 = CreateTextElement1(Nothing, UserForm1.TextBox_Charct1, Point, Matrix3dIdentity)
    Set tCharct2 = CreateTextElement1(Nothing, UserForm1.TextBox_Charct2, Point, Matrix3dIdentity)
    
    numTextIni tHeight
    numTextIni tDiametr
    numTextIni tDist
    StringTextIni tCharct1
    StringTextIni tCharct2
    
    tHRange = tHeight.Boundary
    tDRange = tDiametr.Boundary
    tDistRange = tDist.Boundary
    CellRange1 = mCell1.Range
    Charct1Range = tCharct1.Boundary
    Charct2Range = tCharct2.Boundary

'    Set tmtP = CreateLineElement2(Nothing, CellRange1.Low, CellRange1.Low)
'    tmtP.LineWeight = 3
'    tmtP.Color = 2
'    Set tmtP1 = CreateLineElement2(Nothing, CellRange1.High, CellRange1.High)
'    tmtP1.LineWeight = 3
'    tmtP1.Color = 3
'    Set P1 = CreateLineElement2(Nothing, Point, Point)
'    P1.LineWeight = 3
'    P1.Color = 4
'    tmtP.Redraw DrawMode
'    tmtP1.Redraw DrawMode
'    P1.Redraw DrawMode
    CellGabaritX = CellRange1.High.X - CellRange1.Low.X
    If UserForm1.TextBox_Charct1 <> "" And (Charct1Range.High.X - Charct1Range.Low.X) >= (Charct2Range.High.X - Charct2Range.Low.X) Then
        CharctMaxRangeX = Charct1Range.High.X - Charct1Range.Low.X
    Else
        CharctMaxRangeX = Charct2Range.High.X - Charct2Range.Low.X
    End If
    
    Set dLine = CreateLineElement2(Nothing, Point3dFromXYZ(tDRange.Low.X, Point.Y, Point.Z), Point3dFromXYZ(tDRange.High.X, Point.Y, Point.Z))
    
    tDiametr.Move Point3dFromXYZ(0, -(CDbl(UserForm1.TextBox_FontHeight.Text) + vOffset), 0)
    tHeight.Move Point3dFromXYZ((dLine.Length - (tHRange.High.X - tHRange.Low.X)) * 0.5, vOffset, 0)
    tDist.Move Point3dFromXYZ(dLine.Length + vOffset, -(tDistRange.High.Y - tDistRange.Low.Y) * 0.5, 0)
    mCell1.Move Point3dFromXYZ((-(CellRange1.High.X - Point.X) - vOffset * 1.3), -(CellRange1.High.Y - Point.Y) * 0.5, 0)
    If UserForm1.TextBox_Charct1 <> "" And UserForm1.TextBox_Charct2 <> "" Then
        tCharct1.Move Point3dFromXYZ(-(vOffset * 4 + CellGabaritX + CharctMaxRangeX), vOffset, 0)
        tCharct2.Move Point3dFromXYZ(-(vOffset * 4 + CellGabaritX + CharctMaxRangeX), -(vOffset + Charct2Range.High.Y - Charct2Range.Low.Y), 0)
    ElseIf UserForm1.TextBox_Charct1 <> "" And UserForm1.TextBox_Charct2 = "" Then
        tCharct1.Move Point3dFromXYZ(-(vOffset * 4 + CellGabaritX + CharctMaxRangeX), -(Charct1Range.High.Y - Charct1Range.Low.Y) * 0.5, 0)
    ElseIf UserForm1.TextBox_Charct1 = "" And UserForm1.TextBox_Charct2 <> "" Then
        tCharct2.Move Point3dFromXYZ(-(vOffset * 4 + CellGabaritX + CharctMaxRangeX), -(Charct2Range.High.Y - Charct2Range.Low.Y) * 0.5, 0)
    End If
    
    dLine.Redraw DrawMode
    tHeight.Redraw DrawMode
    tDiametr.Redraw DrawMode
    tDist.Redraw DrawMode
    mCell1.Redraw DrawMode
    tCharct1.Redraw DrawMode
    tCharct2.Redraw DrawMode
    
    
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
    CommandState.StartDynamics
End Sub

Private Sub numTextIni(mTxt As TextElement)
    mTxt.TextStyle.Font = ActiveDesignFile.Fonts(UserForm1.ComboBox_NumberFontText.Text)
    mTxt.TextStyle.Height = CDbl(UserForm1.TextBox_FontHeight.Text)
    mTxt.TextStyle.Width = CDbl(UserForm1.TextBox_FontHeight.Text)
    mTxt.TextStyle.Justification = msdTextJustificationLeftBottom
End Sub

Private Sub StringTextIni(mTxt As TextElement)
    mTxt.TextStyle.Font = ActiveDesignFile.Fonts(UserForm1.ComboBox_textTypeFont.Text)
    mTxt.TextStyle.Height = CDbl(UserForm1.TextBox_FontHeight.Text)
    mTxt.TextStyle.Width = CDbl(UserForm1.TextBox_FontHeight.Text)
    mTxt.TextStyle.Justification = msdTextJustificationLeftBottom
End Sub

Private Sub AddElementToModel(mEle As Element)
    ActiveModelReference.AddElement mEle
    mEle.Level = ActiveDesignFile.Levels.Find(UserForm1.ComboBox_LevelName.Text)
    mEle.Rewrite
    mEle.Redraw
End Sub

Attribute VB_Name = "UserForm1"
Attribute VB_Base = "0{70FD5DFB-991E-4C94-B01E-0D19BF393945}{10FA048A-3B66-483B-8736-F1AE994A4E12}"
Attribute VB_GlobalNameSpace = False
Attribute VB_Creatable = False
Attribute VB_PredeclaredId = True
Attribute VB_Exposed = False
Attribute VB_TemplateDerived = False
Attribute VB_Customizable = False
Option Explicit

Private Sub InitializeCellName()
    Dim MyCellEnum As CellInformationEnumerator
    Dim MyCell As CellInformation
    ComboBox_CellName1.Clear
    If IsCellLibraryAttached Then
        Set MyCellEnum = Application.GetCellInformationEnumerator(False, False)
        While MyCellEnum.MoveNext
            Set MyCell = MyCellEnum.Current
            ComboBox_CellName1.AddItem MyCell.Name
        Wend
    Else
        MsgBox "Библиотека Cell не подключена", vbOKOnly + vbCritical
       ' opSCell.Value = True
    End If
End Sub

Private Sub InitializeLevelName()
    Dim MyModel As ModelReference
    Dim myLevel As Level
    ComboBox_LevelName.Clear
    Set MyModel = ActiveDesignFile.DefaultModelReference
        For Each myLevel In MyModel.Levels
            ComboBox_LevelName.AddItem myLevel.Name
        Next
End Sub
Private Sub InitializeFontName(Cbox As ComboBox)
    Dim MyModel As ModelReference
    Dim myFont As Font
    Cbox.Clear
    Set MyModel = ActiveDesignFile.DefaultModelReference
        For Each myFont In MyModel.DesignFile.Fonts
            Cbox.AddItem myFont.Name
        Next
End Sub

Private Sub ComboBox_CellName1_DblClick(ByVal Cancel As MSForms.ReturnBoolean)
    InitializeCellName
End Sub

Private Sub ComboBox_NumberFontText_Change()

End Sub

Private Sub CommandButton_PlaceCharacteristic_Click()
    CommandState.StartPrimitive New PCE_PlaceCharacteristic, True
End Sub


Private Sub TextBox_cHeight_Change()

End Sub

Private Sub TextBox_FontHeight_Change()

End Sub

Private Sub UserForm_DblClick(ByVal Cancel As MSForms.ReturnBoolean)
    InitializeCellName
End Sub

Private Sub UserForm_Initialize()
    InitializeCellName
    InitializeLevelName
    InitializeFontName ComboBox_NumberFontText
    InitializeFontName ComboBox_textTypeFont
    
End Sub
