Attribute VB_Name = "Module1"
Public Type Gaps
    Gap As LineElement      '   Gap
    tElement As Element '   Корректируемый элемент
    sePoint As Integer      '   0- start ; 1 - End
End Type
Public globalGaps() As Gaps
Public count As Long
Public startHit As Boolean
Public endHit As Boolean
Public minDistStart As Double
Public minDistEnd As Double
Public WriteStart As Double
Public Writeend As Double
Public minGapStart As LineElement
Public minGapEnd As LineElement
Public tLineStart As Element
Public tLineEnd As Element
Public MyTime As Date

Sub Main()
    UserForm_General.Show vbModeless
End Sub

Attribute VB_Name = "PCE_Draw_gap"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents
Public drawGap As LineElement
Public gIndex As Long


Private Sub IPrimitiveCommandEvents_Cleanup()

End Sub

Private Sub IPrimitiveCommandEvents_DataPoint(Point As Point3d, ByVal View As View)

End Sub

Private Sub IPrimitiveCommandEvents_Dynamics(Point As Point3d, ByVal View As View, ByVal DrawMode As MsdDrawingMode)
    Dim pCentre As Point3d
    Dim mCircle As EllipseElement
    Dim mRadius As Double
    Dim lProject As LineElement
    
    Set lProject = CreateLineElement2(Nothing, drawGap.StartPoint, drawGap.EndPoint)
    lProject.Transform Transform3dFromMatrix3dPoint3d(Matrix3dFromScaleFactors(1, 1, 0), Point3dFromXYZ(0, 0, 0))
    mRadius = lProject.Length * 0.6
    pCentre.X = (drawGap.StartPoint.X + drawGap.EndPoint.X) * 0.5
    pCentre.Y = (drawGap.StartPoint.Y + drawGap.EndPoint.Y) * 0.5
    pCentre.Z = (drawGap.StartPoint.Z + drawGap.EndPoint.Z) * 0.5
    Set mCircle = CreateEllipseElement2(Nothing, pCentre, mRadius, mRadius, Matrix3dIdentity)
    mCircle.Color = 3
   ' mCircle.LineStyle = 2
    mCircle.LineWeight = 2
    drawGap.Color = 2
    drawGap.Redraw DrawMode
    mCircle.Redraw DrawMode
End Sub

Private Sub IPrimitiveCommandEvents_Keyin(ByVal Keyin As String)

End Sub

Private Sub IPrimitiveCommandEvents_Reset()
    'CommandState.StopDynamics
    CommandState.StartDefaultCommand
End Sub

Private Sub IPrimitiveCommandEvents_Start()
    CommandState.StartDynamics
End Sub

Attribute VB_Name = "Procedure"
Sub Serach()

Dim inEnum As ElementEnumerator
Dim inFilter As New ElementScanCriteria
Dim srhEnum As ElementEnumerator
Dim srhFilter As New ElementScanCriteria
Dim k As Integer
Dim pStart As Point3d
Dim pEnd As Point3d
Dim shrLine() As Element
Dim inLine() As Element
Dim i As Long
Dim q As Long

Dim complex As ElementEnumerator
Dim j As Long
Dim dist As Double
Dim lGap As LineElement

    If UserForm_General.TextBox_Search_Radius.Text = "" Then
        MsgBox "Задайте радиус поска"
        Exit Sub
    End If
ReDim globalGaps(0)

    inFilter.ExcludeAllTypes
    inFilter.ExcludeAllLevels
    inFilter.IncludeType msdElementTypeLineString
    inFilter.IncludeType msdElementTypeLine
    inFilter.IncludeType msdElementTypeComplexString
    inFilter.IncludeLevel ActiveDesignFile.Levels.Find(UserForm_General.ListBox_ini_Element.Value)
    Set inEnum = ActiveModelReference.Scan(inFilter)
   ' inLine() = inEnum.BuildArrayFromContents
    
    srhFilter.ExcludeAllTypes
    srhFilter.ExcludeAllLevels
    srhFilter.IncludeType msdElementTypeComplexString
    srhFilter.IncludeType msdElementTypeLineString
        For k = 1 To UserForm_General.ListBox_campare_Element.ListCount
            If UserForm_General.ListBox_campare_Element.Selected(k - 1) Then
                srhFilter.IncludeLevel ActiveDesignFile.Levels.Find(UserForm_General.ListBox_campare_Element.List(k - 1))
            End If
        Next k
    Set srhEnum = ActiveModelReference.Scan(srhFilter)
    shrLine() = srhEnum.BuildArrayFromContents
        While inEnum.MoveNext
 '       For q = 0 To UBound(inLine)
            Select Case inEnum.Current.Type
                Case msdElementTypeLineString
                    pStart = inEnum.Current.AsLineElement.StartPoint
                    pEnd = inEnum.Current.AsLineElement.EndPoint
                Case msdElementTypeComplexString
                    pStart = inEnum.Current.AsComplexStringElement.StartPoint
                    pEnd = inEnum.Current.AsComplexStringElement.EndPoint
                Case msdElementTypeLine
                    pStart = inEnum.Current.AsLineElement.StartPoint
                    pEnd = inEnum.Current.AsLineElement.EndPoint
            End Select
                startHit = False
                endHit = False
                WriteStart = False
                Writeend = False
           '     While srhEnum.MoveNext
                For k = 0 To UBound(shrLine)
                    minDistStart = CDbl(UserForm_General.TextBox_Search_Radius.Text) * 0.01
                    minDistEnd = CDbl(UserForm_General.TextBox_Search_Radius.Text) * 0.01
                     If Not (inEnum.Current.FilePosition = shrLine(k).FilePosition) Then
                                Select Case shrLine(k).Type
                                    Case msdElementTypeLineString
                                        If startHit = False Then Procedure.SetMinGap shrLine(k).AsLineElement, pStart, inEnum.Current, 0
                                        If endHit = False Then Procedure.SetMinGap shrLine(k).AsLineElement, pEnd, inEnum.Current, 1
                                    Case msdElementTypeComplexString
                                        Set complex = shrLine(k).AsComplexStringElement.GetSubElements
                                            While complex.MoveNext
                                                Select Case complex.Current.Type
                                                    Case msdElementTypeLineString
                                                        If startHit = False Then Procedure.SetMinGap complex.Current.AsLineElement, pStart, inEnum.Current, 0
                                                        If endHit = False Then Procedure.SetMinGap complex.Current.AsLineElement, pEnd, inEnum.Current, 1
                                                End Select
                                            Wend
                                End Select
                     End If
                Next k
            If startHit = False And WriteStart = True Then Procedure.WriteGap 0
            If endHit = False And Writeend = True Then Procedure.WriteGap 1
            Set minGapStart = Nothing
            Set minGapEnd = Nothing
            Set tLineStart = Nothing
            Set tLineEnd = Nothing
      Wend
     '  Next q
        UserForm_gaps.ListBox_gaps.Clear
            If count > 0 Then
                ReDim Preserve globalGaps(UBound(globalGaps) - 1)
                    For j = 0 To UBound(globalGaps)
                        UserForm_gaps.ListBox_gaps.AddItem FormatNumber(Round(globalGaps(j).Gap.AsLineElement.Length * 100, 3), 3, vbTrue, vbTrue, vbTrue)
                    Next j
            End If
        UserForm_General.Label_gap.Caption = count
        UserForm_gaps.Caption = "Ошибок: " & count
        MyTime = Time
        UserForm_General.Label6.Caption = "Окончание: " & MyTime
        
'+++++++++++++++++ ' Обнуление переменных ++++++++++++++++++
    count = 0
    Erase shrLine
    Erase inLine
End Sub
Sub MoveView(index As Integer, tLine As LineElement)
    Dim pCenter As Point3d
    pCenter.X = (tLine.StartPoint.X + tLine.EndPoint.X) * 0.5
    pCenter.Y = (tLine.StartPoint.Y + tLine.EndPoint.Y) * 0.5
    pCenter.Z = (tLine.StartPoint.Z + tLine.EndPoint.Z) * 0.5
    ActiveDesignFile.Views(index).center = pCenter
    ActiveDesignFile.Views(index).Redraw
End Sub
Sub Correct(corrGap As Gaps)

Dim myEnum As ElementEnumerator
Dim MyLine() As Element
Dim i As Integer

On Error GoTo Errex
    Select Case corrGap.tElement.Type
        Case msdElementTypeLineString
                If corrGap.sePoint = 0 Then
                    If UserForm_gaps.CheckBox_correct_add_vertex.Value = True Then
                        corrGap.tElement.AsLineElement.InsertVertex 0, corrGap.Gap.StartPoint
                    Else
                        corrGap.tElement.AsLineElement.ModifyVertex 0, corrGap.Gap.StartPoint
                    End If
                ElseIf corrGap.sePoint = 1 Then
                    If UserForm_gaps.CheckBox_correct_add_vertex.Value = True Then
                        corrGap.tElement.AsLineElement.InsertVertex corrGap.tElement.AsLineElement.VerticesCount, corrGap.Gap.StartPoint
                    Else
                        corrGap.tElement.AsLineElement.ModifyVertex corrGap.tElement.AsLineElement.VerticesCount - 1, corrGap.Gap.StartPoint
                    End If
                End If
            corrGap.tElement.AsLineElement.Rewrite
            corrGap.tElement.AsLineElement.Redraw
        Case msdElementTypeComplexString
            Set myEnum = corrGap.tElement.AsComplexStringElement.GetSubElements
            MyLine() = myEnum.BuildArrayFromContents
                For i = 0 To UBound(MyLine)
                    If corrGap.sePoint = 0 Then
                        If i = 0 Then
                            If UserForm_gaps.CheckBox_correct_add_vertex.Value = True Then
                                MyLine(0).AsLineElement.InsertVertex 0, corrGap.Gap.StartPoint
                            Else
                                MyLine(0).AsLineElement.AsLineElement.ModifyVertex 0, corrGap.Gap.StartPoint
                            End If
                        End If
                    ElseIf corrGap.sePoint = 1 Then
                        If i = UBound(MyLine) Then
                            If UserForm_gaps.CheckBox_correct_add_vertex.Value = True Then
                                MyLine(0).AsLineElement.InsertVertex MyLine(0).AsLineElement.VerticesCount, corrGap.Gap.StartPoint
                            Else
                                MyLine(0).AsLineElement.ModifyVertex MyLine(0).AsLineElement.VerticesCount - 1, corrGap.Gap.StartPoint
                            End If
                        End If
                    End If
                    MyLine(0).AsLineElement.Rewrite
                    MyLine(0).AsLineElement.Redraw
                Next i
    End Select
Errex:
End Sub

Sub SetMinGap(MyLine As LineElement, pEnding As Point3d, tarLine As Element, sePoint As Integer)
    Dim dist As Double
    dist = Round(DistancetoLine(MyLine, pEnding).Length, 5)
            If dist = 0 Then
                    Select Case sePoint
                        Case 0
                            startHit = True
                        Case 1
                            endHit = True
                    End Select
                Exit Sub
            End If
        Select Case sePoint
            Case 0
                If dist < minDistStart Then
                    Set minGapStart = DistancetoLine(MyLine, pEnding)
                    Set tLineStart = tarLine
                    WriteStart = True
                    minDistStart = dist
                End If
            Case 1
                If dist < minDistEnd Then
                    Set minGapEnd = DistancetoLine(MyLine, pEnding)
                    Set tLineEnd = tarLine
                    Writeend = True
                    minDistEnd = dist
                End If
        End Select
End Sub

Sub WriteGap(sePoint As Integer)
    Select Case sePoint
            Case 0
                Set globalGaps(UBound(globalGaps)).Gap = minGapStart
                Set globalGaps(UBound(globalGaps)).tElement = tLineStart
                globalGaps(UBound(globalGaps)).sePoint = sePoint
                ReDim Preserve globalGaps(UBound(globalGaps) + 1)
                count = count + 1
            Case 1
                Set globalGaps(UBound(globalGaps)).Gap = minGapEnd
                Set globalGaps(UBound(globalGaps)).tElement = tLineEnd
                globalGaps(UBound(globalGaps)).sePoint = sePoint
                ReDim Preserve globalGaps(UBound(globalGaps) + 1)
                count = count + 1
        End Select
End Sub

Function DistancetoLine(iLine As LineElement, iPoint As Point3d) As LineElement
    Dim i As Long ' Индекс билжайшего вертекса
    Dim MinI As Long
    Dim dist As Double
    Dim tmpDist As Double
    For i = 1 To iLine.VerticesCount - 1
       dist = Dist_Segment_to_Point(iLine.Vertex(i), iLine.Vertex(i + 1), iPoint)
            If i = 1 Then
                tmpDist = dist
                MinI = 1
            End If
            If dist < tmpDist Then
            tmpDist = dist
            MinI = i
        End If
    Next i
    Set DistancetoLine = Dist_segment_to_line(iLine.Vertex(MinI), iLine.Vertex(MinI + 1), iPoint)
End Function

'Private Sub DrawPoint(mPoint As Point3d, mColor As Integer)
'    Dim mLne As LineElement
'    Set mLne = CreateLineElement2(Nothing, mPoint, mPoint)
'    mLne.Color = mColor
'    ActiveModelReference.AddElement mLne
'    mLne.Redraw
'End Sub

Private Function Dist_segment_to_line(StartPoint As Point3d, EndPoint As Point3d, iPoint As Point3d) As LineElement
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d

    vPoint = Vector3dSubtractPoint3dPoint3d(iPoint, StartPoint)
    vLine = Vector3dSubtractPoint3dPoint3d(EndPoint, StartPoint)

    c1 = Vector3dDotProduct(vPoint, vLine)
    c2 = Vector3dDotProduct(vLine, vLine)
        If c1 <= 0 Then
            Set Dist_segment_to_line = CreateLineElement2(Nothing, StartPoint, iPoint)
        ElseIf c2 <= c1 Then
            Set Dist_segment_to_line = CreateLineElement2(Nothing, EndPoint, iPoint)
        Else
            k = c1 / c2
            vProject = Vector3dScale(vLine, k)
            pProject = Vector3dAdd(Vector3dFromPoint3d(StartPoint), vProject)
            Set Dist_segment_to_line = CreateLineElement2(Nothing, Point3dFromVector3d(pProject), iPoint)
        End If
End Function

Private Function Dist_Segment_to_Point(StartPoint As Point3d, EndPoint As Point3d, iPoint As Point3d) As Double
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    
    vPoint = Vector3dSubtractPoint3dPoint3d(iPoint, StartPoint)
    vLine = Vector3dSubtractPoint3dPoint3d(EndPoint, StartPoint)
    
    c1 = Vector3dDotProduct(vPoint, vLine)
    c2 = Vector3dDotProduct(vLine, vLine)
        If c1 <= 0 Then
            Dist_Segment_to_Point = Point3dDistance(StartPoint, iPoint)
        ElseIf c2 <= c1 Then
            Dist_Segment_to_Point = Point3dDistance(EndPoint, iPoint)
        Else
            k = c1 / c2
            vProject = Vector3dScale(vLine, k)
            pProject = Vector3dAdd(Vector3dFromPoint3d(StartPoint), vProject)
            Dist_Segment_to_Point = Point3dDistance(Point3dFromVector3d(pProject), iPoint)
        End If
End Function

Attribute VB_Name = "UserForm_General"
Attribute VB_Base = "0{A14B734A-08F9-4847-8F64-7B94CE7E272D}{DC610B2E-C8CE-4D2E-9594-81354292687E}"
Attribute VB_GlobalNameSpace = False
Attribute VB_Creatable = False
Attribute VB_PredeclaredId = True
Attribute VB_Exposed = False
Attribute VB_TemplateDerived = False
Attribute VB_Customizable = False
Private Sub inizialize_ListBox(MyListBox As ListBox)
    Dim myLevel As Level
    Dim MyLevelName() As String
    ReDim MyLevelName(0)
    Dim MadeChange As Boolean
    Dim i As Integer
    Dim tmpName As String
    
        MyListBox.Clear
    For Each myLevel In ActiveDesignFile.Levels
        MyLevelName(UBound(MyLevelName)) = myLevel.Name
        ReDim Preserve MyLevelName(UBound(MyLevelName) + 1)
    Next
        ReDim Preserve MyLevelName(UBound(MyLevelName) - 1)
        
        MadeChange = True
        While MadeChange = True
            MadeChange = False
            For i = LBound(MyLevelName) To UBound(MyLevelName) - 1
                If StrComp(MyLevelName(i), MyLevelName(i + 1)) = 1 Then
                    tmpName = MyLevelName(i)
                    MyLevelName(i) = MyLevelName(i + 1)
                    MyLevelName(i + 1) = tmpName
                    MadeChange = True
                End If
            Next i
        Wend
        For i = LBound(MyLevelName) To UBound(MyLevelName)
            MyListBox.AddItem MyLevelName(i)
        Next i
End Sub
Private Sub CommandButton_SerchGap_Click()
    MyTime = Time
    UserForm_General.Label5.Caption = "Начало: " & MyTime
    Procedure.Serach
End Sub

Private Sub CommandButton_show_gaps_Click()
    UserForm_gaps.Show vbModeless
End Sub

Private Sub Label6_Click()

End Sub

Private Sub UserForm_Initialize()
    inizialize_ListBox ListBox_ini_Element
    inizialize_ListBox ListBox_campare_Element
End Sub

Attribute VB_Name = "UserForm_gaps"
Attribute VB_Base = "0{A9540C77-F2B5-460A-97A5-3032EAB2AC9B}{63611D2A-1728-4C35-9AB5-DF6E2E16343C}"
Attribute VB_GlobalNameSpace = False
Attribute VB_Creatable = False
Attribute VB_PredeclaredId = True
Attribute VB_Exposed = False
Attribute VB_TemplateDerived = False
Attribute VB_Customizable = False
Private Sub CheckBox_in_radius_Change()
    If UserForm_gaps.CheckBox_in_radius.Value = True Then
        UserForm_gaps.TextBox_radius.Enabled = True
        UserForm_gaps.CommandButton_Correct_All.Caption = "Исправить все в радиусе"
    Else
        UserForm_gaps.TextBox_radius.Enabled = False
        UserForm_gaps.CommandButton_Correct_All.Caption = "Исправить все"
    End If
End Sub
Private Sub UserForm_QueryClose(Cancel As Integer, CloseMode As Integer)
    Cancel = 1
    UserForm_gaps.Hide
End Sub
'Private Sub CommandButton_close_Click()
'    UserForm_gaps.Hide
'End Sub
Private Sub CommandButton_Correct_All_Click()
    Dim i As Long
        If UserForm_gaps.TextBox_radius.Text = "" And UserForm_gaps.TextBox_radius.Enabled = True Then
            MsgBox "Задайте радиус поиска"
        Else
            For i = 0 To UBound(globalGaps)
                If UserForm_gaps.TextBox_radius.Enabled = False Then
                    Procedure.Correct globalGaps(i)
                ElseIf UserForm_gaps.TextBox_radius.Enabled = True Then
                    If globalGaps(i).Gap.Length <= CDbl(UserForm_gaps.TextBox_radius.Text) * 0.01 Then
                        Procedure.Correct globalGaps(i)
                    End If
                End If
            Next i
        End If
    Procedure.Serach
End Sub

Private Sub CommandButton_correct_single_Click()
On Error GoTo Myerr
    Procedure.Correct globalGaps(UserForm_gaps.ListBox_gaps.ListIndex)
   ' Procedure.Serach
Myerr:
End Sub

Private Sub ListBox_gaps_Change()
    Dim dynGaps As New PCE_Draw_gap
If UserForm_gaps.ListBox_gaps.ListCount > 0 Then
    Procedure.MoveView 1, globalGaps(UserForm_gaps.ListBox_gaps.ListIndex).Gap
    Set dynGaps.drawGap = globalGaps(UserForm_gaps.ListBox_gaps.ListIndex).Gap
    CommandState.StartPrimitive dynGaps
End If
End Sub
'Private Sub UserForm_QueryClose(Cancel As Integer, CloseMode As Integer)
'   Cancel = 1
'End Sub
