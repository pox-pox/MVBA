Attribute VB_Name = "LCE_Edit"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private Const attrId As Long = 22352


Private Sub ILocateCommandEvents_Accept(ByVal Element As Element, Point As Point3d, ByVal View As View)
   ' MsgBox "rere"
  '  GetLinkage CurrentMarker
'    CurrentMarker.Color = 3
'    CurrentMarker.Rewrite
'    CurrentMarker.Redraw
End Sub

Private Sub ILocateCommandEvents_Cleanup()

End Sub

Private Sub ILocateCommandEvents_Dynamics(Point As Point3d, ByVal View As View, ByVal DrawMode As MsdDrawingMode)

End Sub

Private Sub ILocateCommandEvents_LocateFailed()

End Sub

Private Sub ILocateCommandEvents_LocateFilter(ByVal Element As Element, Point As Point3d, Accepted As Boolean)
    Accepted = False
        If Element.Type = msdElementTypeEllipse Then
            Accepted = True
            Set CurrentMarker = Element.AsEllipseElement
            GetLinkage CurrentMarker
           ' CommandState.StartDefaultCommand
        End If
End Sub

Private Sub ILocateCommandEvents_LocateReset()
    CommandState.StartDefaultCommand
End Sub

Private Sub ILocateCommandEvents_Start()
    'CommandState.EnableAccuSnap
End Sub

Private Sub GetLinkage(MyEle As Element)
    Dim dblk() As DataBlock
    Dim name As String
    Dim SplitAtr() As String
    
    dblk = MyEle.GetUserAttributeData(attrId)
    dblk(0).CopyString name, False
    SplitAtr = Split(name, ";")
    UserForm_General.Label_span_.Caption = SplitAtr(0)
    UserForm_General.Label_station.Caption = SplitAtr(1)
    UserForm_General.Label_offset.Caption = SplitAtr(2)
    UserForm_General.ComboBox_Feature.Text = SplitAtr(3)
    UserForm_General.ComboBox_Description.Text = SplitAtr(4)
End Sub

Attribute VB_Name = "LCE_SetSpan"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private Const attrId As Long = 22352

Implements ILocateCommandEvents

Private Sub ILocateCommandEvents_Accept(ByVal Element As Element, Point As Point3d, ByVal View As View)
    Dim i As Long ' Индекс билжайшего вертекса
    Dim j As Long ' Индекс оси
    Dim k As Long
    Dim l As Long
    
    
    IndexView = View.Index
    i = Element.AsLineElement.GetClosestSegment(Point)
    CurrentLine = GetLinkage(Element.AsLineElement)
    For l = 0 To CurrentLine - 1
        k = k + CounVertex(l)
    Next l
    ButtonEnabled2
    UserForm_General.Label_span_.Caption = GetSpanByPoint(CurrentLine, i)
    UserForm_General.Label_span.Caption = CurrentSegment - k + CounVertex(CurrentLine - 1) + 1 & "/" & CounVertex(CurrentLine - 1) - 1
    UserForm_General.CommandButton_next_Line.Caption = "Line:" & CurrentLine & "/" & UBound(CounVertex) + 1
    fixSpan = True
    UserForm_General.Label_span.Font.Bold = True
End Sub

Private Sub ILocateCommandEvents_Cleanup()

End Sub

Private Sub ILocateCommandEvents_Dynamics(Point As Point3d, ByVal View As View, ByVal DrawMode As MsdDrawingMode)

End Sub

Private Sub ILocateCommandEvents_LocateFailed()

End Sub

Private Sub ILocateCommandEvents_LocateFilter(ByVal Element As Element, Point As Point3d, Accepted As Boolean)
    Accepted = False
    
        If Element.Type = msdElementTypeLine Or msdElementTypeLineString Then
            Accepted = True
            ShowCommand "Фиксация пролета"
            ShowPrompt "Подтвердите ЛКМ"
        End If
End Sub

Private Sub ILocateCommandEvents_LocateReset()

End Sub

Private Sub ILocateCommandEvents_Start()
    ShowCommand "Фиксация пролета"
    ShowPrompt "Укажите пролет"
End Sub

Private Function GetLinkage(MyEle As LineElement) As Integer
    Dim dblk() As DataBlock
    Dim name As Integer
    
    dblk = MyEle.GetUserAttributeData(attrId)
    dblk(0).CopyInteger name, False
    GetLinkage = (name)
End Function

Private Function GetSpanByPoint(MyIndex As Long, MyVertex As Long)
    Dim i As Long
    Dim j As Long
    
    For i = 0 To UBound(Lines)
        If Lines(i).Index = MyIndex Then
            If j = MyVertex Then
                GetSpanByPoint = Lines(i).ID & "-" & Lines(i + 1).ID
                CurrentSegment = i
                Exit For
            ElseIf j <> MyVertex Then
                j = j + 1
            End If
        End If
    Next i
End Function

Private Sub ButtonEnabled2()
    With UserForm_General
        .CommandButton_Edit.Enabled = True
        .CommandButton_next_Line.Enabled = True
        .CommandButton_nextSpan.Enabled = True
        .CommandButton_Place_marker.Enabled = True
        .CommandButton_previousSpan.Enabled = True
        .CommandButton_Save.Enabled = True
        .CommandButton_Settings.Enabled = True
        .Label_span.Enabled = True
    End With
End Sub

Attribute VB_Name = "LCE_Set_Coridor"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private Const attrId As Long = 22352

Private ReCentreline As LineElement      ' Осевая для перепривязки
Private SetCorridor As ShapeElement      ' Буфер
Private BSetCorridor As Boolean          ' Выбран буфер
Private Sub ILocateCommandEvents_Accept(ByVal Element As Element, Point As Point3d, ByVal View As View)
  '  BSetCorridor = True
    ReJoinByReference
    CommandState.StartDefaultCommand
    
End Sub
Private Sub ILocateCommandEvents_Cleanup()
    CommandState.StartDefaultCommand
End Sub
Private Sub ILocateCommandEvents_Dynamics(Point As Point3d, ByVal View As View, ByVal DrawMode As MsdDrawingMode)

End Sub
Private Sub ILocateCommandEvents_LocateFailed()

End Sub
Private Sub ILocateCommandEvents_LocateFilter(ByVal Element As Element, Point As Point3d, Accepted As Boolean)
    Accepted = False
    
            If Element.Type = msdElementTypeShape Then
                Accepted = True
                Set SetCorridor = Element.AsShapeElement
              ' CommandState.StartDefaultCommand
            End If
End Sub
Private Sub ILocateCommandEvents_LocateReset()
    CommandState.StartDefaultCommand

End Sub
Private Sub ILocateCommandEvents_Start()
    If UserForm_General.CheckBox_inside_corridor.Value = False Then
        ReJoinByReference
        CommandState.StartDefaultCommand
    End If
    ShowCommand "Вкопирование маркеров"
    ShowPrompt "Укажите коридор"
End Sub


Private Sub ReJoinByReference()
    Dim myAttach As Attachment
    Dim myFilter As New ElementScanCriteria
    Dim myEnum As ElementEnumerator
    Dim i As Integer
    Dim MyCorridor() As Point3d
    
    Set myAttach = ActiveDesignFile.DefaultModelReference.Attachments(UserForm_General.cmbReference.ListIndex + 1)
    myFilter.ExcludeAllTypes
    myFilter.ExcludeAllLevels
    myFilter.IncludeType msdElementTypeEllipse
    myFilter.IncludeLevel myAttach.Levels.Find(UserForm_Settings.TextBox_Level_of_marker.Text)
    
    Set myEnum = myAttach.Scan(myFilter)
        If UserForm_General.CheckBox_inside_corridor.Value = True Then
          '  CommandState.StartLocate New LCE_Set_Coridor
               ' If BSetCorridor = True Then
                    MyCorridor = SetCorridor.GetVertices
                    While myEnum.MoveNext
                        Select Case myEnum.Current.Type
                            Case msdElementTypeEllipse
                                If Point3dInPolygonXY(myEnum.Current.AsEllipseElement.CenterPoint, MyCorridor) = 1 Then
                                    ReJoin myEnum.Current.AsEllipseElement
                                    i = i + 1
                                End If
                        End Select
                    Wend
                    MsgBox "Вкопировано: " & i
               ' End If
           ' BSetCorridor = False
        ElseIf UserForm_General.CheckBox_inside_corridor.Value = False Then
            While myEnum.MoveNext
                Select Case myEnum.Current.Type
                    Case msdElementTypeEllipse
                        ReJoin myEnum.Current.AsEllipseElement
                        i = i + 1
                End Select
            Wend
        MsgBox "Вкопировано: " & i
        End If
    
End Sub

Private Sub ReJoin(ReMarker As Element)
    Dim MyPoint As LineElement
    Dim vPlanar As Vector3d
    Dim segment As LineElement
    Dim i As Long ' Индекс билжайшего вертекса
    Dim vtSegment As Vector3d
    Dim vtStation As Vector3d
    Dim StartPoint As LineElement
    Dim EndPoint As LineElement
    Dim projectPoint As Point3d ' Проекция точки на сегмнет
    Dim StartP As Point3d
    Dim EndP As Point3d
    Dim Angle As Double
    Dim j As Long
    Dim t As Long
    Dim NewMarker As EllipseElement
    Dim vStation As Vector3d
    Dim vPoint As Vector3d
    Dim lOffset As Double
    Dim Mpoint As Point3d ' Центр маркера
    Dim SaveFeature As String
    Dim SaveDescription As String
    Dim Attribut As String
    Dim dblk As New DataBlock
    Dim dblkW() As DataBlock
    Dim name As String
    Dim SplitAtr() As String
    Dim MSpan As String
    
    Mpoint = ReMarker.AsEllipseElement.CenterPoint
    
    FindNerstLine Mpoint
    i = ReCentreline.GetClosestSegment(Mpoint)
    CurrentLine = GetLinkageId(ReCentreline)
    MSpan = GetSpanByPoint(GetLinkageId(ReCentreline), i)
    
    StartP = Point3dFromXYZ(Lines(CurrentSegment).X, Lines(CurrentSegment).Y, 0)
    EndP = Point3dFromXYZ(Lines(CurrentSegment + 1).X, Lines(CurrentSegment + 1).Y, 0)
    
    vPlanar = Vector3dFromXYZ(0, 0, 1)
    
    vtSegment = Vector3dSubtractPoint3dPoint3d(EndP, StartP)
    Set segment = CreateLineElement2(Nothing, StartP, EndP)
    projectPoint = segment.ProjectPointOnPerpendicular(Mpoint, Matrix3dIdentity)
    vStation = Vector3dSubtractPoint3dPoint3d(EndP, StartP)
    vPoint = Vector3dSubtractPoint3dPoint3d(Mpoint, StartP)
    Angle = Vector3dPlanarAngleBetweenVectors(vStation, vPoint, vPlanar)
    vtStation = Vector3dSubtractPoint3dPoint3d(projectPoint, StartP)
        If Angle > Pi / 2 Or Angle < -Pi / 2 Then
            StartP = Point3dFromXYZ(Lines(CurrentSegment - 1).X, Lines(CurrentSegment - 1).Y, 0)
            EndP = Point3dFromXYZ(Lines(CurrentSegment).X, Lines(CurrentSegment).Y, 0)
            Set segment = CreateLineElement2(Nothing, StartP, EndP)
            projectPoint = segment.ProjectPointOnPerpendicular(Mpoint, Matrix3dIdentity)
        End If
    
    Set lCurrentStation = CreateLineElement2(Nothing, StartP, projectPoint)
    Set lCurrentOffset = CreateLineElement2(Nothing, projectPoint, Mpoint)
    lCurrentStation.Transform Transform3dFromMatrix3dPoint3d(Matrix3dFromScaleFactors(1, 1, 0), Point3dFromXYZ(0, 0, 0))
    lCurrentOffset.Transform Transform3dFromMatrix3dPoint3d(Matrix3dFromScaleFactors(1, 1, 0), Point3dFromXYZ(0, 0, 0))
    
    lOffset = lCurrentOffset.Length
    
    If Angle > 0 Then
        lOffset = -lOffset
    End If
    
    dblkW = ReMarker.GetUserAttributeData(attrId)
    dblkW(0).CopyString name, False
    SplitAtr = Split(name, ";")
   
    SaveFeature = SplitAtr(3)
    SaveDescription = SplitAtr(4)
    Attribut = MSpan & ";" & CStr(myRound(lCurrentStation.Length)) & ";" & CStr(myRound(lOffset)) & ";" & SaveFeature & ";" & SaveDescription
    dblk.CopyString Attribut, True
    
    Set NewMarker = CreateEllipseElement2(Nothing, Mpoint, CDbl(UserForm_Settings.TextBox_Size_marker.Text), CDbl(UserForm_Settings.TextBox_Size_marker.Text), Matrix3dIdentity)
    NewMarker.Level = ActiveDesignFile.Levels.Find(CheckLevel(UserForm_Settings.TextBox_Level_of_marker.Text).name)
    ActiveSettings.Level = ActiveDesignFile.Levels.Find(CheckLevel(UserForm_Settings.TextBox_Level_of_marker.Text).name)
    ActiveModelReference.AddElement NewMarker
    NewMarker.Redraw
    
    
    NewMarker.AddUserAttributeData attrId, dblk
    NewMarker.Rewrite
    
    
End Sub
Function myRound(Value As Double) As String
    myRound = FormatNumber(Round(Value, CInt(2)), CInt(2), vbTrue, vbFalse, vbTrue)
End Function
Function CheckLevel(LevelName As String) As Level ' Проверка файла на наличие слоя, если нет, то создает
    Dim MyLevel As Level
    On Error Resume Next
    
    Set CheckLevel = ActiveDesignFile.Levels(LevelName)
   If Err.Number <> 0 Then
        Set MyLevel = ActiveDesignFile.AddNewLevel(LevelName)
        ActiveDesignFile.Levels.Rewrite
        Set CheckLevel = MyLevel
    End If
   Err.Clear
End Function
Private Sub FindNerstLine(EndPoint As Point3d)
    Dim myEnum As ElementEnumerator
    Dim ComlexString As ElementEnumerator
    Dim myFilter As New ElementScanCriteria
    Dim i As Long
    
    Dim minDistance As Double
    Dim tLineString As LineElement
  '  Dim j As Long
  '  Dim o As Long
    Dim movePoint As Point3d
    Dim tmpDist As Double
    
    Dim Mysegment As LineElement
    Dim myprojectPoint As Point3d ' Проекция точки на сегмнет
    
    minDistance = 500000000
    
    myFilter.ExcludeAllTypes
    myFilter.IncludeType msdElementTypeLineString
    myFilter.IncludeType msdElementTypeLine
    myFilter.IncludeType msdElementTypeComplexString
    
        myFilter.ExcludeAllLevels
        myFilter.IncludeLevel ActiveDesignFile.Levels.Find(UserForm_Settings.TextBox_Centreline.Text)
        
    Set myEnum = ActiveModelReference.Scan(myFilter)
        While myEnum.MoveNext
            Select Case myEnum.Current.Type
                Case msdElementTypeLineString
                    tmpDist = DistancetoLine(myEnum.Current.AsLineElement, EndPoint)
                    If tmpDist < minDistance Then
                        If tmpDist > 0 Then
                            minDistance = tmpDist
                            Set ReCentreline = myEnum.Current.AsLineElement
                        End If
                    End If
                Case msdElementTypeLine
                    Set Mysegment = CreateLineElement2(Nothing, myEnum.Current.AsLineElement.StartPoint, myEnum.Current.AsLineElement.EndPoint)
                    myprojectPoint = Mysegment.ProjectPointOnPerpendicular2(EndPoint, Matrix3dIdentity)
                    tmpDist = Point3dDistanceXY(myprojectPoint, EndPoint)
                    If tmpDist < minDistance Then
                        If tmpDist > 0 Then
                            minDistance = tmpDist
                            Set ReCentreline = myEnum.Current.AsLineElement
                        End If
                    End If
                Case msdElementTypeComplexString
                    Set ComlexString = myEnum.Current.AsComplexStringElement.GetSubElements
                        While ComlexString.MoveNext
                            Select Case ComlexString.Current.Type
                                Case msdElementTypeLineString
                                    tmpDist = DistancetoLine(ComlexString.Current.AsLineElement, EndPoint)
                                    If tmpDist < minDistance Then
                                        If tmpDist > 0 Then
                                            minDistance = tmpDist
                                            Set ReCentreline = ComlexString.Current.AsLineElement
                                        End If
                                    End If
                            End Select
                        Wend
            End Select
        Wend
End Sub

Private Function DistancetoLine(iLine As LineElement, iPoint As Point3d) As Double
    Dim segment As LineElement
    Dim i As Long ' Индекс билжайшего вертекса
    Dim projectPoint As Point3d ' Проекция точки на сегмнет
    Dim Perp As LineElement
    
    i = iLine.GetClosestSegment(iPoint)
    Set segment = CreateLineElement2(Nothing, iLine.Vertex(i + 1), iLine.Vertex(i + 2))
    projectPoint = segment.ProjectPointOnPerpendicular2(iPoint, Matrix3dIdentity)
    DistancetoLine = Point3dDistanceXY(projectPoint, iPoint)

End Function

Private Function GetLinkageId(MyEle As LineElement) As Integer
    Dim dblk() As DataBlock
    Dim name As Integer
    
    dblk = MyEle.GetUserAttributeData(attrId)
    dblk(0).CopyInteger name, False
    GetLinkageId = (name)
End Function
Private Function GetSpanByPoint(MyIndex As Long, MyVertex As Long) As String
    
    Dim i As Long
    Dim j As Long
    
    For i = 0 To UBound(Lines)
        If Lines(i).Index = MyIndex Then
            If j = MyVertex Then
                GetSpanByPoint = Lines(i).ID & "-" & Lines(i + 1).ID
                CurrentSegment = i
                Exit For
            ElseIf j <> MyVertex Then
                j = j + 1
            End If
        End If
    Next i
   ' j = 0

End Function

Attribute VB_Name = "PCE_Place_marker"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private Const attrId As Long = 22352
Private Station As LineElement
Private Offset As LineElement
Private lOffset As Double
Private lstation As Double
Private vStation As Vector3d
Private vPoint As Vector3d
Private Centreline As LineElement
Implements IPrimitiveCommandEvents
Option Explicit
Private Declare Function FindWindow Lib "user32" Alias "FindWindowA" (ByVal lpClassName As Any, ByVal lpWindowName As Any) As Long
Private Declare Function SetForegroundWindow Lib "user32" (ByVal hwnd As Long) As Long
Sub MicroStationWindowToForeground()
    Dim rtc As Long
    rtc = SetForegroundWindow(FindWindow("MstnTop", vbNullString))
End Sub

Private Sub IPrimitiveCommandEvents_Cleanup()

End Sub

Private Sub IPrimitiveCommandEvents_DataPoint(Point As Point3d, ByVal View As View)
    Dim MyPoint As LineElement
 '   Dim MyCircle As EllipseElement
    
    ViewIndex = View.Index
    Set CurrentMarker = CreateEllipseElement2(Nothing, Point, CDbl(UserForm_Settings.TextBox_Size_marker.Text), CDbl(UserForm_Settings.TextBox_Size_marker.Text), Matrix3dIdentity)
    CurrentMarker.Level = ActiveDesignFile.Levels.Find(CheckLevel(UserForm_Settings.TextBox_Level_of_marker.Text).name)
    ActiveSettings.Level = ActiveDesignFile.Levels.Find(CheckLevel(UserForm_Settings.TextBox_Level_of_marker.Text).name)
    ActiveModelReference.AddElement CurrentMarker
    CurrentMarker.Redraw
    ActiveModelReference.AddElement lCurrentStation
    lCurrentStation.Redraw
    ActiveModelReference.AddElement lCurrentOffset
    lCurrentOffset.Redraw
    bPlaceMarker = True
'    Set MyPoint = CreateLineElement2(Nothing, Point, Point)
'    ActiveModelReference.AddElement MyPoint
'    MyPoint.Redraw
 '   AddLinkage CurrentMarker
    
    CommandState.StopDynamics
    CommandState.StartDefaultCommand

End Sub

Private Sub IPrimitiveCommandEvents_Dynamics(Point As Point3d, ByVal View As View, ByVal DrawMode As MsdDrawingMode)
    Dim MyPoint As LineElement
    Dim vPlanar As Vector3d
    Dim segment As LineElement
    Dim i As Long ' Индекс билжайшего вертекса
    Dim vtSegment As Vector3d
    Dim vtStation As Vector3d
    Dim StartPoint As LineElement
    Dim EndPoint As LineElement
    Dim projectPoint As Point3d ' Проекция точки на сегмнет
    Dim StartP As Point3d
    Dim EndP As Point3d
    Dim Angle As Double
    Dim j As Long
    Dim t As Long
    

    
    IndexView = View.Index
    
    If fixSpan = False Then
        FindNerstLine Point
        i = Centreline.GetClosestSegment(Point)
        CurrentLine = GetLinkage(Centreline)
        GetSpanByPoint GetLinkage(Centreline), i
    
    
    
        For t = 0 To CurrentLine - 1
            j = j + CounVertex(t)
        Next t
        UpdateLabels j
    End If
    
    StartP = Point3dFromXYZ(Lines(CurrentSegment).X, Lines(CurrentSegment).Y, 0)
    EndP = Point3dFromXYZ(Lines(CurrentSegment + 1).X, Lines(CurrentSegment + 1).Y, 0)
    
    vPlanar = Vector3dFromXYZ(0, 0, 1)
    Set MyPoint = CreateLineElement2(Nothing, Point, Point)
    MyPoint.Redraw DrawMode
    
    vtSegment = Vector3dSubtractPoint3dPoint3d(EndP, StartP)
    Set segment = CreateLineElement2(Nothing, StartP, EndP)
    projectPoint = segment.ProjectPointOnPerpendicular(Point, Matrix3dIdentity)
    vStation = Vector3dSubtractPoint3dPoint3d(EndP, StartP)
    vPoint = Vector3dSubtractPoint3dPoint3d(Point, StartP)
    Angle = Vector3dPlanarAngleBetweenVectors(vStation, vPoint, vPlanar)
    vtStation = Vector3dSubtractPoint3dPoint3d(projectPoint, StartP)
        If fixSpan = False Then
            If Angle > Pi / 2 Or Angle < -Pi / 2 Then
                StartP = Point3dFromXYZ(Lines(CurrentSegment - 1).X, Lines(CurrentSegment - 1).Y, 0)
                EndP = Point3dFromXYZ(Lines(CurrentSegment).X, Lines(CurrentSegment).Y, 0)
                Set segment = CreateLineElement2(Nothing, StartP, EndP)
                projectPoint = segment.ProjectPointOnPerpendicular(Point, Matrix3dIdentity)
            End If
        End If
    
    Set lCurrentStation = CreateLineElement2(Nothing, StartP, projectPoint)
    Set lCurrentOffset = CreateLineElement2(Nothing, projectPoint, Point)
    Set StartPoint = CreateLineElement2(Nothing, StartP, StartP)
    Set EndPoint = CreateLineElement2(Nothing, EndP, EndP)
'    lCurrentStation.Transform Transform3dFromMatrix3dPoint3d(Matrix3dFromScaleFactors(1, 1, 0), Point3dFromXYZ(0, 0, 0))
'    lCurrentOffset.Transform Transform3dFromMatrix3dPoint3d(Matrix3dFromScaleFactors(1, 1, 0), Point3dFromXYZ(0, 0, 0))
    StartPoint.LineWeight = 9
    StartPoint.Color = 2
    EndPoint.LineWeight = 9
    EndPoint.Color = 3
    lCurrentStation.LineWeight = 2
    lCurrentStation.Color = 4
    lCurrentOffset.LineWeight = 2
    lCurrentOffset.Color = 4
    
    lCurrentStation.Redraw DrawMode
    lCurrentOffset.Redraw DrawMode
    StartPoint.Redraw DrawMode
    EndPoint.Redraw DrawMode
    
    
    lOffset = lCurrentOffset.Length
    
        If Angle > 0 Then
            lOffset = -lOffset
        End If
        
     UserForm_General.Label_station.Caption = myRound(lCurrentStation.Length)
        If fixSpan = True Then
            If Angle > Pi / 2 Or Angle < -Pi / 2 Then
               ' If Station.Length > 0 Then
                  '  lstation = Station.Length
                    UserForm_General.Label_station.Caption = myRound(-lCurrentStation.Length)
              '  End If
            End If
        End If
    UserForm_General.Label_offset.Caption = myRound(lOffset)
    UserForm_General.Label_span_.Caption = Lines(CurrentSegment).ID & "-" & Lines(CurrentSegment + 1).ID
    
End Sub

Private Sub IPrimitiveCommandEvents_Keyin(ByVal Keyin As String)

End Sub

Private Sub IPrimitiveCommandEvents_Reset()
    CommandState.StartDefaultCommand
End Sub

Private Sub IPrimitiveCommandEvents_Start()
    Dim Point As Point3d
    
    CommandState.EnableAccuSnap
    CommandState.StartDynamics
   
        If UserForm_General.ComboBox_Feature.ListCount > 0 Then
            UserForm_General.ComboBox_Feature.ListIndex = -1
            UserForm_General.ComboBox_Description.ListIndex = -1
        End If
    MicroStationWindowToForeground
End Sub

Private Sub AddLinkage(MyEle As Element)
    Dim dblk As New DataBlock
    Dim Attribut As String
    Attribut = UserForm_General.Label_span_.Caption & ";" & UserForm_General.Label_station.Caption & ";" & UserForm_General.Label_offset.Caption & ";" & UserForm_General.ComboBox_Feature.Text & ";" & UserForm_General.ComboBox_Description.Text
    dblk.CopyString Attribut, True
    MyEle.AddUserAttributeData attrId, dblk
    MyEle.Rewrite
End Sub

Function myRound(Value As Double) As String
    myRound = FormatNumber(Round(Value, CInt(2)), CInt(2), vbTrue, vbFalse, vbTrue)
End Function

Function CheckLevel(LevelName As String) As Level ' Проверка файла на наличие слоя, если нет, то создает
    Dim MyLevel As Level
    On Error Resume Next
    
    Set CheckLevel = ActiveDesignFile.Levels(LevelName)
   If Err.Number <> 0 Then
        Set MyLevel = ActiveDesignFile.AddNewLevel(LevelName)
        ActiveDesignFile.Levels.Rewrite
        Set CheckLevel = MyLevel
    End If
   Err.Clear
End Function

Private Sub FindNerstLine(EndPoint As Point3d)
    Dim myEnum As ElementEnumerator
    Dim ComlexString As ElementEnumerator
    Dim myFilter As New ElementScanCriteria
    Dim i As Long
    
    Dim minDistance As Double
    Dim tLineString As LineElement
  '  Dim j As Long
  '  Dim o As Long
    Dim movePoint As Point3d
    Dim tmpDist As Double
    
    Dim Mysegment As LineElement
    Dim myprojectPoint As Point3d ' Проекция точки на сегмнет
    
    minDistance = 500000000
    
    myFilter.ExcludeAllTypes
    myFilter.IncludeType msdElementTypeLineString
    myFilter.IncludeType msdElementTypeLine
    myFilter.IncludeType msdElementTypeComplexString
    
        myFilter.ExcludeAllLevels
        myFilter.IncludeLevel ActiveDesignFile.Levels.Find(UserForm_Settings.TextBox_Centreline.Text)
        
    Set myEnum = ActiveModelReference.Scan(myFilter)
        While myEnum.MoveNext
            Select Case myEnum.Current.Type
                Case msdElementTypeLineString
                    tmpDist = DistancetoLine(myEnum.Current.AsLineElement, EndPoint)
                    If tmpDist < minDistance Then
                        If tmpDist > 0 Then
                            minDistance = tmpDist
                            Set Centreline = myEnum.Current.AsLineElement
                        End If
                    End If
                Case msdElementTypeLine
                    Set Mysegment = CreateLineElement2(Nothing, myEnum.Current.AsLineElement.StartPoint, myEnum.Current.AsLineElement.EndPoint)
                    myprojectPoint = Mysegment.ProjectPointOnPerpendicular2(EndPoint, Matrix3dIdentity)
                    tmpDist = Point3dDistanceXY(myprojectPoint, EndPoint)
                    If tmpDist < minDistance Then
                        If tmpDist > 0 Then
                            minDistance = tmpDist
                            Set Centreline = myEnum.Current.AsLineElement
                        End If
                    End If
                Case msdElementTypeComplexString
                    Set ComlexString = myEnum.Current.AsComplexStringElement.GetSubElements
                        While ComlexString.MoveNext
                            Select Case ComlexString.Current.Type
                                Case msdElementTypeLineString
                                    tmpDist = DistancetoLine(ComlexString.Current.AsLineElement, EndPoint)
                                    If tmpDist < minDistance Then
                                        If tmpDist > 0 Then
                                            minDistance = tmpDist
                                            Set Centreline = ComlexString.Current.AsLineElement
                                        End If
                                    End If
                            End Select
                        Wend
            End Select
        Wend
End Sub

Private Function DistancetoLine(iLine As LineElement, iPoint As Point3d) As Double
    Dim segment As LineElement
    Dim i As Long ' Индекс билжайшего вертекса
    Dim projectPoint As Point3d ' Проекция точки на сегмнет
    Dim Perp As LineElement
    
    i = iLine.GetClosestSegment(iPoint)
    Set segment = CreateLineElement2(Nothing, iLine.Vertex(i + 1), iLine.Vertex(i + 2))
    projectPoint = segment.ProjectPointOnPerpendicular2(iPoint, Matrix3dIdentity)
    DistancetoLine = Point3dDistanceXY(projectPoint, iPoint)

End Function

Private Function GetLinkage(MyEle As LineElement) As Integer
    Dim dblk() As DataBlock
    Dim name As Integer
    
    dblk = MyEle.GetUserAttributeData(attrId)
    dblk(0).CopyInteger name, False
    GetLinkage = (name)
End Function

Private Function GetSpanByPoint(MyIndex As Long, MyVertex As Long) As String
    
    Dim i As Long
    Dim j As Long
    
    For i = 0 To UBound(Lines)
        If Lines(i).Index = MyIndex Then
            If j = MyVertex Then
                GetSpanByPoint = Lines(i).ID & "-" & Lines(i + 1).ID
                CurrentSegment = i
                Exit For
            ElseIf j <> MyVertex Then
                j = j + 1
            End If
        End If
    Next i
   ' j = 0

End Function

Private Sub UpdateLabels(j As Long)
        UserForm_General.Label_span.Caption = CurrentSegment - j + CounVertex(CurrentLine - 1) + 1 & "/" & CounVertex(CurrentLine - 1) - 1
    '   UserForm_General.Label_span_.Caption = Lines(CurrentSegment).ID & "-" & Lines(CurrentSegment + 1).ID
        UserForm_General.CommandButton_next_Line.Caption = "Line:" & CurrentLine & "/" & UBound(CounVertex) + 1
End Sub

Attribute VB_Name = "Procedure"
Option Explicit
Private Const attrId As Long = 22352

Declare Function mdlDialog_fileOpen Lib "stdmdlbltin.dll" (ByVal _
    fileName As String, ByVal rFileH As Long, ByVal _
    resourceId As Long, ByVal suggestedFileName As String, _
    ByVal filterString As String, ByVal defaultDirectory As String, _
    ByVal titleString As String) As Long
    
Public Type Centrelines
    Index As Integer
    ID As String
    X As Double
    Y As Double
    Z As Double
    Span As Double
End Type

Public Type Towers
    ID As String
    X As Double
    Y As Double
    Z As Double
End Type

Public Type TSpan
    From As String
    ToStructure As String
    Lengh As Double
    Feature As String
    Station As Double
    Offset As Double
    Description As String
End Type

Public Type TMarker
    Span As String
    Station As Double
    Offset As Double
    Feature As String
    Descript As String
End Type

Public Lines() As Centrelines
Public MyTowers() As Towers
Public XLSLoadBool As Boolean
Public PTSLoadBool As Boolean
Public CurrentLine As Long
Public CurrentSegment As Long
Public IndexView As Integer
Public CounVertex() As Long
Public MarkAttr As TMarker
Public PositionLeft As Single
Public PositionTop As Single
Public CurrentMarker As EllipseElement  ' Текущий элемент для редактирования
Public lCurrentStation As LineElement   ' отображение Station
Public lCurrentOffset As LineElement    ' отображение Offset
Public bPlaceMarker As Boolean          ' Ключ нанесения маркера
Public ViewIndex As Integer
Public fixSpan As Boolean
'Public ReCentreline As LineElement      ' Осевая для перепривязки
'Public SetCorridor As ShapeElement      ' Буфер
'Public BSetCorridor As Boolean          ' Выбран буфер

Sub Main()
   ' BSetCorridor = False
    UserForm_General.Show vbModeless
End Sub

Attribute VB_Name = "UserForm_General"
Attribute VB_Base = "0{B6E77840-61F5-4B05-9F5C-E3D97D7A2530}{C21F7EEC-2DF7-4F11-944A-64D7CDC65F5B}"
Attribute VB_GlobalNameSpace = False
Attribute VB_Creatable = False
Attribute VB_PredeclaredId = True
Attribute VB_Exposed = False
Attribute VB_TemplateDerived = False
Attribute VB_Customizable = False
Option Explicit
Private Declare Function FindWindow Lib "user32" Alias "FindWindowA" (ByVal lpClassName As Any, ByVal lpWindowName As Any) As Long
Private Declare Function SetForegroundWindow Lib "user32" (ByVal hwnd As Long) As Long


Private Const attrId As Long = 22352
Sub MicroStationWindowToForeground()
    Dim rtc As Long
    rtc = SetForegroundWindow(FindWindow("MstnTop", vbNullString))
End Sub

Private Sub CommandButton_Delete_Click()
    If bPlaceMarker = True Then
        ActiveModelReference.RemoveElement lCurrentStation
        lCurrentStation.Redraw
        ActiveModelReference.RemoveElement lCurrentOffset
        
        lCurrentOffset.Redraw
        ActiveModelReference.RemoveElement CurrentMarker
        CurrentMarker.Redraw
        ActiveDesignFile.Views(ViewIndex).Redraw
        
        bPlaceMarker = False
    End If

End Sub

Private Sub CommandButton_Draw_CLine_Click()
    DrawLines
End Sub

Private Sub CommandButton_DrawID_Click()
    DrawID
End Sub

Private Sub CommandButton_Edit_Click()
'    UserForm_General.Show vbModeless
'    UserForm_General.Left = PositionLeft
'    UserForm_General.Top = PositionTop
    MicroStationWindowToForeground
    CommandState.StartLocate New LCE_Edit
End Sub

Private Sub CommandButton_load_pts_Click()
    LoadPtc
End Sub

Private Sub CommandButton_load_xls_Click()
    LoadSettXLS
End Sub

Private Sub CommandButton_next_Line_Click()
    Dim i As Long
    Dim j As Long
    
    CurrentLine = CurrentLine + 1
        If CurrentLine > UBound(CounVertex) + 1 Then CurrentLine = 1
    
        For i = 0 To CurrentLine - 1
            j = j + CounVertex(i)
        Next i
    CurrentSegment = j - CounVertex(CurrentLine - 1)
    FitSpan CurrentLine, CurrentSegment
    UpdateLabels j
'        UserForm_General.Label_span.Caption = CurrentSegment - j + CounVertex(CurrentLine - 1) + 1 & "/" & CounVertex(CurrentLine - 1) - 1
'        UserForm_General.Label_span_.Caption = Lines(CurrentSegment).ID & "-" & Lines(CurrentSegment + 1).ID
'        UserForm_General.Label_line.Caption = CurrentLine & "/" & UBound(CounVertex) + 1
        
End Sub

Private Sub CommandButton_nextSpan_Click()
    Dim i As Long
    Dim j As Long
    For i = 0 To CurrentLine - 1
        j = j + CounVertex(i)
    Next i
'    j = j - CounVertex(CurrentLine - 1)
    If CurrentSegment < j - 2 Then
        CurrentSegment = CurrentSegment + 1
        FitSpan CurrentLine, CurrentSegment
        UpdateLabels j
'        UserForm_General.Label_span.Caption = CurrentSegment - j + CounVertex(CurrentLine - 1) + 1 & "/" & CounVertex(CurrentLine - 1) - 1
'        UserForm_General.Label_span_.Caption = Lines(CurrentSegment).ID & "-" & Lines(CurrentSegment + 1).ID
    End If
End Sub

Private Sub CommandButton_Place_marker_Click()
    
'    UserForm_General.Show vbModeless
'    UserForm_General.Left = PositionLeft
'    UserForm_General.Top = PositionTop
    CommandState.StartPrimitive New PCE_Place_marker, True
End Sub

Private Sub CommandButton_previousSpan_Click()
    Dim i As Long
    Dim j As Long
    

    For i = 0 To CurrentLine - 1
        j = j + CounVertex(i)
    Next i
'    j = j - CounVertex(CurrentLine - 1)
    If CurrentSegment > j - CounVertex(CurrentLine - 1) Then
        CurrentSegment = CurrentSegment - 1
        FitSpan CurrentLine, CurrentSegment
        UpdateLabels j
'        UserForm_General.Label_span.Caption = CurrentSegment - j + CounVertex(CurrentLine - 1) + 1 & "/" & CounVertex(CurrentLine - 1) - 1
    End If
End Sub

Private Sub CommandButton_ReJoin_Click()
    CommandState.StartLocate New LCE_Set_Coridor
    
End Sub

Private Sub CommandButton_Reload_ref_Click()
    InitializationReference
End Sub

Private Sub CommandButton_Save_Click()
    Save
     
End Sub

Private Sub CommandButton_saveAttr_Click()
On Error GoTo Handler
    AddLinkageReSave CurrentMarker
    If bPlaceMarker = True Then
        ActiveModelReference.RemoveElement lCurrentStation
        ActiveModelReference.RemoveElement lCurrentOffset
        lCurrentStation.Redraw
        lCurrentOffset.Redraw
         ActiveDesignFile.Views(ViewIndex).Redraw
        bPlaceMarker = False
    End If
Handler:
End Sub

Private Sub CommandButton_Set_Line_Click()
'    UserForm_Forma.Show vbModeless
    MicroStationWindowToForeground
    CommandState.StartLocate New LCE_SetSpan
End Sub


Private Sub CommandButton_Settings_Click()
    UserForm_Settings.Show vbModeless
End Sub

'Private Sub CommandButton1_Click()
'    UserForm_Forma.Show vbModeless
'    CommandState.StartPrimitive New PCE_Place_marker, True
'End Sub

'Private Sub CommandButton2_Click()
'    UserForm_Forma.Show vbModeless
'    CommandState.StartLocate New LCE_Edit
'End Sub

Private Sub UpdateLabels(j As Long)
        UserForm_General.Label_span.Caption = CurrentSegment - j + CounVertex(CurrentLine - 1) + 1 & "/" & CounVertex(CurrentLine - 1) - 1
        UserForm_General.Label_span_.Caption = Lines(CurrentSegment).ID & "-" & Lines(CurrentSegment + 1).ID
        UserForm_General.CommandButton_next_Line.Caption = "Line:" & CurrentLine & "/" & UBound(CounVertex) + 1
End Sub

Private Sub DrawID()
    Dim i As Long
    Dim StringID As TextElement
    Dim PString As Point3d
        For i = 0 To UBound(Lines)
            PString.X = Lines(i).X
            PString.Y = Lines(i).Y
            PString.Z = Lines(i).Z
            ActiveSettings.TextStyle.Font = ActiveDesignFile.Fonts("Arial")
            Set StringID = CreateTextElement1(Nothing, Lines(i).ID, PString, Matrix3dIdentity)
            StringID.TextStyle.Font = ActiveDesignFile.Fonts("Arial")
            StringID.TextStyle.Height = 5
            StringID.TextStyle.Width = 5
            StringID.TextStyle.Justification = msdTextJustificationLeftBottom
            ActiveModelReference.AddElement StringID
            StringID.Redraw
        Next i
End Sub

Private Sub DrawLines()
    Dim LVertexes() As Point3d
    Dim MyLine As LineElement
    ReDim LVertexes(0)
    Dim i As Long
    
    For i = 0 To UBound(Lines)
        If i < UBound(Lines) Then
            If Lines(i).Index = Lines(i + 1).Index Then
                LVertexes(UBound(LVertexes)).X = Lines(i).X
                LVertexes(UBound(LVertexes)).Y = Lines(i).Y
                LVertexes(UBound(LVertexes)).Z = Lines(i).Z
                ReDim Preserve LVertexes(UBound(LVertexes) + 1)
            ElseIf Lines(i).Index + 1 = Lines(i + 1).Index Then
                LVertexes(UBound(LVertexes)).X = Lines(i).X
                LVertexes(UBound(LVertexes)).Y = Lines(i).Y
                LVertexes(UBound(LVertexes)).Z = Lines(i).Z
                Set MyLine = CreateLineElement1(Nothing, LVertexes)
                MyLine.Color = Lines(i).Index
                ActiveModelReference.AddElement MyLine
                MyLine.Level = ActiveDesignFile.Levels.Find(CheckLevel(UserForm_Settings.TextBox_Centreline.Text).name)
                MyLine.Redraw
                AddLinkage MyLine, Lines(i).Index
                ReDim Preserve LVertexes(0)
            End If
        ElseIf i = UBound(Lines) Then
            LVertexes(UBound(LVertexes)).X = Lines(i).X
            LVertexes(UBound(LVertexes)).Y = Lines(i).Y
            LVertexes(UBound(LVertexes)).Z = Lines(i).Z
            Set MyLine = CreateLineElement1(Nothing, LVertexes)
            MyLine.Color = Lines(i).Index
            ActiveModelReference.AddElement MyLine
            MyLine.Level = ActiveDesignFile.Levels.Find(CheckLevel(UserForm_Settings.TextBox_Centreline.Text).name)
            MyLine.Redraw
            AddLinkage MyLine, Lines(i).Index
        End If
    Next i
End Sub

'Private Sub AddLinkage(MyEle As Element, link As Integer)
'    Dim dblk As New DataBlock
'
'    dblk.CopyInteger link, True
'    MyEle.AddUserAttributeData attrId, dblk
'    MyEle.Rewrite
'End Sub

Function CheckLevel(LevelName As String) As Level ' Проверка файла на наличие слоя, если нет, то создает
    Dim MyLevel As Level
    On Error Resume Next
    
    Set CheckLevel = ActiveDesignFile.Levels(LevelName)
   If Err.Number <> 0 Then
        Set MyLevel = ActiveDesignFile.AddNewLevel(LevelName)
        ActiveDesignFile.Levels.Rewrite
        Set CheckLevel = MyLevel
    End If
   Err.Clear
End Function

Private Sub AddLinkageReSave(MyEle As Element)
    Dim dblk As New DataBlock
    Dim Attribut As String
    Attribut = UserForm_General.Label_span_.Caption & ";" & UserForm_General.Label_station.Caption & ";" & UserForm_General.Label_offset.Caption & ";" & UserForm_General.ComboBox_Feature.Text & ";" & UserForm_General.ComboBox_Description.Text
    dblk.CopyString Attribut, True
    MyEle.DeleteUserAttributeData attrId, 0
    MyEle.AddUserAttributeData attrId, dblk
    MyEle.Rewrite
End Sub

Private Sub LoadSettXLS()
    Dim strFName As String
    Dim lngfhandle As Long
    Dim lngrid As Long
    Dim retVal As Long
    Dim PathXls As String
    Dim myExcel As Excel.Application
    Dim myWorkbook As Excel.Workbook
    Dim CurrSheet As Worksheet
    Dim curRow As Long
    Dim i As Long ' Порядковый номер Оси
    Dim j As Long ' Количество вертексов в оси
    Set myExcel = CreateObject("Excel.Application")
    strFName = Space(255)
    
    curRow = 3 ' Начинать поиск со сторой строки
    i = 1
    ReDim Lines(0)
    ReDim CounVertex(0)
    
    retVal = mdlDialog_fileOpen(strFName, lngfhandle, lngrid, "", "*.xls", _
                                    ActiveDesignFile.Path, "Открыть файл Specification")
    Select Case retVal
        Case 0 'Open
            PathXls = Left(strFName, InStr(1, strFName, Chr(0)) - 1)
            
            Set myWorkbook = myExcel.Workbooks.Open(PathXls)
         '   Set myExcel = Nothing
            
            Set CurrSheet = myWorkbook.Worksheets(1)
                While Not (CurrSheet.Cells(curRow, 1) = "" And CurrSheet.Cells(curRow + 1, 1) = "")
                    If CurrSheet.Cells(curRow, 1) <> "" Then
                        Lines(UBound(Lines)).Index = i
                        Lines(UBound(Lines)).ID = CurrSheet.Cells(curRow, 2)
                        Debug.Print Lines(UBound(Lines)).Index & Lines(UBound(Lines)).ID
                        j = j + 1
                    ElseIf CurrSheet.Cells(curRow, 1) = "" Then
                        i = i + 1
                        ReDim Preserve Lines(UBound(Lines) - 1)
                        CounVertex(UBound(CounVertex)) = j
                        ReDim Preserve CounVertex(UBound(CounVertex) + 1)
                        j = 0
                    End If
                ReDim Preserve Lines(UBound(Lines) + 1)
                curRow = curRow + 1
                Wend
                CounVertex(UBound(CounVertex)) = j
                'ReDim Preserve CounVertex(UBound(CounVertex) - 1)
                ReDim Preserve Lines(UBound(Lines) - 1)
                XLSLoadBool = True
                If PTSLoadBool = True Then
                    JoinCoordinates
                    XLSLoadBool = False
                    ButtomEnabled1
                End If
            MsgBox "Файл Specification загружен:" & vbCr & strFName
        Case 1 'Cancel
            MsgBox "Файл не выделен"
    End Select
    myExcel.Quit
End Sub

Private Sub LoadPtc()
    Dim strFName As String
    Dim lngfhandle As Long
    Dim lngrid As Long
    Dim retVal As Long
    Dim PathPTS As String
    Dim FFile As Long
    Dim TextLine As String
    Dim XSplit() As String
    
    ReDim MyTowers(0)
    
    strFName = Space(255)
    retVal = mdlDialog_fileOpen(strFName, lngfhandle, lngrid, "", "*.pts", _
                                    ActiveDesignFile.Path, "Открыть файл с координатами опор")
    Select Case retVal
        Case 0 'Open
            PathPTS = Left(strFName, InStr(1, strFName, Chr(0)) - 1)
            FFile = FreeFile
            Open PathPTS For Input As #FFile
            While EOF(FFile) = False
                Line Input #FFile, TextLine
                XSplit = Split(TextLine, vbTab)
                MyTowers(UBound(MyTowers)).ID = XSplit(0)
                MyTowers(UBound(MyTowers)).X = CDbl(XSplit(1))
                MyTowers(UBound(MyTowers)).Y = CDbl(XSplit(2))
                MyTowers(UBound(MyTowers)).Z = CDbl(XSplit(3))
                Debug.Print MyTowers(UBound(MyTowers)).ID & vbTab & MyTowers(UBound(MyTowers)).X & vbTab & MyTowers(UBound(MyTowers)).Y
                ReDim Preserve MyTowers(UBound(MyTowers) + 1)
            Wend
                ReDim Preserve MyTowers(UBound(MyTowers) - 1)
                PTSLoadBool = True
            MsgBox "Файл координат опор загружен загружен:" & vbCr & strFName
            If XLSLoadBool = True Then
                JoinCoordinates
                PTSLoadBool = False
                ButtomEnabled1
            End If
        Case 1 'Cancel
            MsgBox "Файл не выделен"
    End Select
End Sub
Private Sub JoinCoordinates()
    Dim i As Long
    Dim j As Long
    Dim k As Long ' Счетчик сопоставленных опор
    For i = 0 To UBound(Lines)
        Debug.Print "+Lines: " & Lines(i).ID
        For j = 0 To UBound(MyTowers)
            If Lines(i).ID = MyTowers(j).ID Then
                Lines(i).X = MyTowers(j).X
                Lines(i).Y = MyTowers(j).Y
                Lines(i).Z = MyTowers(j).Z
                k = k + 1
               Debug.Print "Lines: " & Lines(i).ID
            End If
        Next j
    Next i
    MsgBox "Сопоставлено: " & k & "/" & UBound(Lines) + 1
End Sub

Private Sub AddLinkage(MyEle As Element, link As Integer)
    Dim dblk As New DataBlock
    
    dblk.CopyInteger link, True
    MyEle.AddUserAttributeData attrId, dblk
    MyEle.Rewrite
End Sub

Private Sub FitSpan(Line As Long, Span As Long)
    Dim pCenter As Point3d
    pCenter.X = (Lines(CurrentSegment).X + Lines(CurrentSegment + 1).X) * 0.5
    pCenter.Y = (Lines(CurrentSegment).Y + Lines(CurrentSegment + 1).Y) * 0.5
    pCenter.Z = (Lines(CurrentSegment).X + Lines(CurrentSegment + 1).Z) * 0.5
    ActiveDesignFile.Views(IndexView).Center = pCenter
    ActiveDesignFile.Views(IndexView).Redraw
End Sub

Private Sub Save()
    Dim myEnum As ElementEnumerator
    Dim myFilter As New ElementScanCriteria
    Dim MyMarkers() As Element
    Dim i As Long
    Dim j As Long
    Dim Table() As TSpan
    Dim FirstRecord As Boolean

    Dim strFName As String
    Dim lngfhandle As Long
    Dim lngrid As Long
    Dim retVal As Long
    Dim PathXls As String
    Dim myExcel As Excel.Application
    Dim myWorkbook As Excel.Workbook
    Dim CurrSheet As Worksheet
    Set myExcel = CreateObject("Excel.Application")
    Dim curRow As Long
    Dim k As Long
    Dim SpanEnd As Boolean
    Dim UpSpan As Long
    Dim DownSpan As Long
    Dim SpanOK As Double ' Есть запись в пролете
    
    strFName = Space(255)
    SpanOK = False
    
    ReDim Table(0)
    myFilter.ExcludeAllTypes
    myFilter.ExcludeAllLevels
    myFilter.IncludeLevel ActiveDesignFile.Levels.Find(UserForm_Settings.TextBox_Level_of_marker.Text)
    myFilter.IncludeType msdElementTypeEllipse
    Set myEnum = ActiveModelReference.Scan(myFilter)
    MyMarkers() = myEnum.BuildArrayFromContents
    
    If UBound(MyMarkers) >= 0 Then
        For i = 0 To UBound(Lines) - 1
            For j = 0 To UBound(MyMarkers)
                GetLinkage MyMarkers(j)
                If MarkAttr.Span = Lines(i).ID & "-" & Lines(i + 1).ID Then
                    If Not FirstRecord Then
                        Table(UBound(Table)).From = Lines(i).ID
                        Table(UBound(Table)).ToStructure = Lines(i + 1).ID
                        Table(UBound(Table)).Lengh = Sqr((Lines(i + 1).X - Lines(i).X) ^ 2 + (Lines(i + 1).Y - Lines(i).Y) ^ 2)
                        Table(UBound(Table)).Feature = MarkAttr.Feature
                        Table(UBound(Table)).Station = MarkAttr.Station
                        Table(UBound(Table)).Offset = MarkAttr.Offset
                        Table(UBound(Table)).Description = MarkAttr.Descript
                        ReDim Preserve Table(UBound(Table) + 1)
    '                   FirstRecord = False
                        SpanOK = True
                    End If
                End If
            Next j
                If SpanOK = False Then
                    If Lines(i).Index = Lines(i + 1).Index Then
                        Table(UBound(Table)).From = Lines(i).ID
                        Table(UBound(Table)).ToStructure = Lines(i + 1).ID
                        Table(UBound(Table)).Lengh = Sqr((Lines(i + 1).X - Lines(i).X) ^ 2 + (Lines(i + 1).Y - Lines(i).Y) ^ 2)
                        ReDim Preserve Table(UBound(Table) + 1)
                    End If
                End If
            SpanOK = False
        Next i
        ReDim Preserve Table(UBound(Table) - 1)
        
        curRow = 6
        DownSpan = False
        retVal = mdlDialog_fileOpen(strFName, lngfhandle, lngrid, "", "*.xls", _
                                        ActiveDesignFile.Path, "Сохранить таблицу изменений")
        Select Case retVal
            Case 0 'Open
                PathXls = Left(strFName, InStr(1, strFName, Chr(0)) - 1)
               ' MsgBox "Файл Specification загружен:" & vbCr & strFName
                Set myWorkbook = myExcel.Workbooks.Open(PathXls)
         '       Set myExcel = Nothing
        '        myExcel.Quit
                Set CurrSheet = myWorkbook.Worksheets(1)
                FirstRecord = False
                SpanEnd = False
                    For k = 0 To UBound(Table)
                        If FirstRecord = False Then
                            CurrSheet.Cells(curRow, 1) = Table(k).From
                            CurrSheet.Cells(curRow, 2) = Table(k).ToStructure
                            CurrSheet.Cells(curRow, 3) = myRound(Table(k).Lengh)
                            CurrSheet.Cells(curRow, 4) = Table(k).Feature
                                If Table(k).Station <> 0 And Table(k).Offset <> 0 Then
                                    CurrSheet.Cells(curRow, 5) = Table(k).Station
                                    CurrSheet.Cells(curRow, 6) = Table(k).Offset
                                    CurrSheet.Range(CurrSheet.Cells(curRow, 1), CurrSheet.Cells(curRow, 7)).Interior.Color = RGB(204, 255, 204)
                                End If
                            CurrSheet.Cells(curRow, 7) = Table(k).Description
                            FirstRecord = True
                            curRow = curRow + 1
                            k = k + 1
                        End If
                        If UBound(Table) > 0 Then
                            If Table(k).From & Table(k).ToStructure = Table(k - 1).From & Table(k - 1).ToStructure Then
    '                            CurrSheet.Cells(curRow, 1) = Table(k).From
    '                            CurrSheet.Cells(curRow, 2) = Table(k).ToStructure
                                'CurrSheet.Cells(curRow, 3) = Table(k).Lengh
                                CurrSheet.Cells(curRow, 4) = Table(k).Feature
                                CurrSheet.Cells(curRow, 5) = Table(k).Station
                                CurrSheet.Cells(curRow, 6) = Table(k).Offset
                                CurrSheet.Cells(curRow, 7) = Table(k).Description
                                    If SpanEnd = False Then
                                       UpSpan = 6 + k - 1
                                    End If
                                curRow = curRow + 1
                                DownSpan = DownSpan + 1
                                SpanEnd = True
                                If k = UBound(Table) Then SpanEnd = False
                            ElseIf Table(k).From & Table(k).ToStructure <> Table(k - 1).From & Table(k - 1).ToStructure Then
                                CurrSheet.Cells(curRow, 1) = Table(k).From
                                CurrSheet.Cells(curRow, 2) = Table(k).ToStructure
                                CurrSheet.Cells(curRow, 3) = myRound(Table(k).Lengh)
                                CurrSheet.Cells(curRow, 4) = Table(k).Feature
                                If Table(k).Station <> 0 And Table(k).Offset <> 0 Then
                                    CurrSheet.Cells(curRow, 5) = Table(k).Station
                                    CurrSheet.Cells(curRow, 6) = Table(k).Offset
                                    CurrSheet.Range(CurrSheet.Cells(curRow, 1), CurrSheet.Cells(curRow, 7)).Interior.Color = RGB(204, 255, 204)
                                End If
                                CurrSheet.Cells(curRow, 7) = Table(k).Description
                             '   CurrSheet.Range(CurrSheet.Cells(curRow, 1), CurrSheet.Cells(curRow, 7)).Interior.Color = RGB(204, 255, 204)
                                curRow = curRow + 1
                                SpanEnd = False
                            End If
                        End If
                        If SpanEnd = False And DownSpan > 0 Then
                           CurrSheet.Range(CurrSheet.Cells(UpSpan, 4), CurrSheet.Cells(UpSpan + DownSpan, 7)).Sort CurrSheet.Cells(UpSpan, 5), xlAscending
                           CurrSheet.Range(CurrSheet.Cells(UpSpan, 1), CurrSheet.Cells(UpSpan, 7)).Interior.Color = RGB(204, 255, 204)
                           CurrSheet.Range(CurrSheet.Cells(UpSpan + 1, 4), CurrSheet.Cells(UpSpan + DownSpan, 7)).Interior.Color = RGB(255, 255, 255)
                           
                           DownSpan = 0
                        End If
                    Next k
                CurrSheet.Columns("A:B").AutoFit
                    For i = 1 To 7
                        CurrSheet.Range(CurrSheet.Cells(6, i), CurrSheet.Cells(UBound(Table) + 6, i)).Borders.Weight = xlThin
                        CurrSheet.Range(CurrSheet.Cells(6, i), CurrSheet.Cells(UBound(Table) + 6, i)).Borders(xlEdgeLeft).Weight = 3
                        CurrSheet.Range(CurrSheet.Cells(6, i), CurrSheet.Cells(UBound(Table) + 6, i)).Borders(xlEdgeRight).Weight = 3
                        CurrSheet.Range(CurrSheet.Cells(6, i), CurrSheet.Cells(UBound(Table) + 6, i)).Borders(xlEdgeBottom).Weight = 3
                    Next i
                
              '  CurrSheet.Range(CurrSheet.Cells(UpSpan, 4), CurrSheet.Cells(UpSpan + DownSpan, 7)).Interior.Color = RGB(204, 255, 204)
                
                ''''''******************* Сортировка в пределах пролета***********************************************
       '         CurrSheet.Range("A6:D15").Sort CurrSheet.Range("E6"), xlAscending
                
     '           CurrSheet.Range(CurrSheet.Cells(6, 1), CurrSheet.Cells(14, 7)).Sort CurrSheet.Cells(curRow, 5), xlAscending
                
                
    '            curRow = 6
    '                For k = curRow To UBound(Table)
    '
    '
    '                Next k
           '     myWorkbook.Save
                myExcel.Quit
    
            Case 1 'Cancel
                MsgBox "Файл не выделен"
        End Select
    Else
        MsgBox " Маркеры не найдены"
    End If


End Sub

Private Sub GetLinkage(MyEle As Element)
    Dim dblk() As DataBlock
    Dim name As String
    Dim SplitAtr() As String
    Dim SplitSpan() As String
    
    dblk = MyEle.GetUserAttributeData(attrId)
    dblk(0).CopyString name, False
    SplitAtr = Split(name, ";")
'    SplitSpan = Split(SplitAtr(0), "-")
    MarkAttr.Span = SplitAtr(0)
    MarkAttr.Station = SplitAtr(1)
    MarkAttr.Offset = SplitAtr(2)
    MarkAttr.Feature = SplitAtr(3)
    MarkAttr.Descript = SplitAtr(4)
    
End Sub

Private Sub ButtomEnabled1()
    UserForm_General.CommandButton_Set_Line.Enabled = True
    UserForm_General.CommandButton_Draw_CLine.Enabled = True
    UserForm_General.CommandButton_DrawID.Enabled = True
    UserForm_General.CommandButton_Settings.Enabled = True
    UserForm_General.CommandButton_Save.Enabled = True
    UserForm_General.MultiPage1.Pages(1).Enabled = True
    UserForm_General.MultiPage1.Pages(2).Enabled = True
End Sub

Function myRound(Value As Double) As String
    myRound = FormatNumber(Round(Value, CInt(2)), CInt(2), vbTrue, vbFalse, vbTrue)
End Function
Sub InitializationReference()
Dim MyModel As ModelReference
Dim myAttachment As Attachment
UserForm_General.cmbReference.Clear
Set MyModel = ActiveDesignFile.DefaultModelReference

    For Each myAttachment In MyModel.Attachments
        Debug.Print myAttachment.AttachName
        UserForm_General.cmbReference.AddItem myAttachment.AttachName
        myAttachment.LogicalName = myAttachment.AttachName
    Next
   If UserForm_General.cmbReference.ListCount > 0 Then UserForm_General.cmbReference.ListIndex = 0
End Sub
'Private Sub ReJoinByReference()
'    Dim myAttach As Attachment
'    Dim myFilter As New ElementScanCriteria
'    Dim myEnum As ElementEnumerator
'    Dim i As Integer
'    Dim MyCorridor() As Point3d
'
'    Set myAttach = ActiveDesignFile.DefaultModelReference.Attachments(UserForm_General.cmbReference.ListIndex + 1)
'    myFilter.ExcludeAllTypes
'    myFilter.ExcludeAllLevels
'    myFilter.IncludeType msdElementTypeEllipse
'    myFilter.IncludeLevel myAttach.Levels.Find(UserForm_Settings.TextBox_Level_of_marker.Text)
'
'    Set myEnum = myAttach.Scan(myFilter)
'        If UserForm_General.CheckBox_inside_corridor.Enabled = True Then
'            CommandState.StartLocate New LCE_Set_Coridor
'                If BSetCorridor = True Then
'                    MyCorridor = SetCorridor.GetVertices
'                    While myEnum.MoveNext
'                        Select Case myEnum.Current.Type
'                            Case msdElementTypeEllipse
'                                If Point3dInPolygonXY(myEnum.Current.AsEllipseElement.CenterPoint, MyCorridor) = 1 Then
'                                    ReJoin myEnum.Current.AsEllipseElement
'                                    i = i + 1
'                                End If
'                        End Select
'                    Wend
'                    MsgBox "Вкопировано: " & i
'                End If
'            BSetCorridor = False
'        ElseIf UserForm_General.CheckBox_inside_corridor.Enabled = False Then
'            While myEnum.MoveNext
'                Select Case myEnum.Current.Type
'                    Case msdElementTypeEllipse
'                        ReJoin myEnum.Current.AsEllipseElement
'                        i = i + 1
'                End Select
'            Wend
'        MsgBox "Вкопировано: " & i
'        End If
'
'End Sub

'Private Sub ReJoin(ReMarker As Element)
'    Dim MyPoint As LineElement
'    Dim vPlanar As Vector3d
'    Dim segment As LineElement
'    Dim i As Long ' Индекс билжайшего вертекса
'    Dim vtSegment As Vector3d
'    Dim vtStation As Vector3d
'    Dim StartPoint As LineElement
'    Dim EndPoint As LineElement
'    Dim projectPoint As Point3d ' Проекция точки на сегмнет
'    Dim StartP As Point3d
'    Dim EndP As Point3d
'    Dim Angle As Double
'    Dim j As Long
'    Dim t As Long
'    Dim NewMarker As EllipseElement
'    Dim vStation As Vector3d
'    Dim vPoint As Vector3d
'    Dim lOffset As Double
'    Dim Mpoint As Point3d ' Центр маркера
'    Dim SaveFeature As String
'    Dim SaveDescription As String
'    Dim Attribut As String
'    Dim dblk As New DataBlock
'    Dim dblkW() As DataBlock
'    Dim name As String
'    Dim SplitAtr() As String
'    Dim MSpan As String
'
'    Mpoint = ReMarker.AsEllipseElement.CenterPoint
'
'    FindNerstLine Mpoint
'    i = ReCentreline.GetClosestSegment(Mpoint)
'    CurrentLine = GetLinkageId(ReCentreline)
'    MSpan = GetSpanByPoint(GetLinkageId(ReCentreline), i)
'
'    StartP = Point3dFromXYZ(Lines(CurrentSegment).X, Lines(CurrentSegment).Y, 0)
'    EndP = Point3dFromXYZ(Lines(CurrentSegment + 1).X, Lines(CurrentSegment + 1).Y, 0)
'
'    vPlanar = Vector3dFromXYZ(0, 0, 1)
'
'    vtSegment = Vector3dSubtractPoint3dPoint3d(EndP, StartP)
'    Set segment = CreateLineElement2(Nothing, StartP, EndP)
'    projectPoint = segment.ProjectPointOnPerpendicular(Mpoint, Matrix3dIdentity)
'    vStation = Vector3dSubtractPoint3dPoint3d(EndP, StartP)
'    vPoint = Vector3dSubtractPoint3dPoint3d(Mpoint, StartP)
'    Angle = Vector3dPlanarAngleBetweenVectors(vStation, vPoint, vPlanar)
'    vtStation = Vector3dSubtractPoint3dPoint3d(projectPoint, StartP)
'        If Angle > Pi / 2 Or Angle < -Pi / 2 Then
'            StartP = Point3dFromXYZ(Lines(CurrentSegment - 1).X, Lines(CurrentSegment - 1).Y, 0)
'            EndP = Point3dFromXYZ(Lines(CurrentSegment).X, Lines(CurrentSegment).Y, 0)
'            Set segment = CreateLineElement2(Nothing, StartP, EndP)
'            projectPoint = segment.ProjectPointOnPerpendicular(Mpoint, Matrix3dIdentity)
'        End If
'
'    Set lCurrentStation = CreateLineElement2(Nothing, StartP, projectPoint)
'    Set lCurrentOffset = CreateLineElement2(Nothing, projectPoint, Mpoint)
'    lCurrentStation.Transform Transform3dFromMatrix3dPoint3d(Matrix3dFromScaleFactors(1, 1, 0), Point3dFromXYZ(0, 0, 0))
'    lCurrentOffset.Transform Transform3dFromMatrix3dPoint3d(Matrix3dFromScaleFactors(1, 1, 0), Point3dFromXYZ(0, 0, 0))
'
'    lOffset = lCurrentOffset.Length
'
'    If Angle > 0 Then
'        lOffset = -lOffset
'    End If
'
'    dblkW = ReMarker.GetUserAttributeData(attrId)
'    dblkW(0).CopyString name, False
'    SplitAtr = Split(name, ";")
'
'    SaveFeature = SplitAtr(3)
'    SaveDescription = SplitAtr(4)
'    Attribut = MSpan & ";" & CStr(myRound(lCurrentStation.Length)) & ";" & CStr(myRound(lOffset)) & ";" & SaveFeature & ";" & SaveDescription
'    dblk.CopyString Attribut, True
'
'    Set NewMarker = CreateEllipseElement2(Nothing, Mpoint, CDbl(UserForm_Settings.TextBox_Size_marker.Text), CDbl(UserForm_Settings.TextBox_Size_marker.Text), Matrix3dIdentity)
'    NewMarker.Level = ActiveDesignFile.Levels.Find(CheckLevel(UserForm_Settings.TextBox_Level_of_marker.Text).name)
'    ActiveSettings.Level = ActiveDesignFile.Levels.Find(CheckLevel(UserForm_Settings.TextBox_Level_of_marker.Text).name)
'    ActiveModelReference.AddElement NewMarker
'    NewMarker.Redraw
'
'
'    NewMarker.AddUserAttributeData attrId, dblk
'    NewMarker.Rewrite
'
'
'End Sub
'
'Private Sub FindNerstLine(EndPoint As Point3d)
'    Dim myEnum As ElementEnumerator
'    Dim ComlexString As ElementEnumerator
'    Dim myFilter As New ElementScanCriteria
'    Dim i As Long
'
'    Dim minDistance As Double
'    Dim tLineString As LineElement
'  '  Dim j As Long
'  '  Dim o As Long
'    Dim movePoint As Point3d
'    Dim tmpDist As Double
'
'    Dim Mysegment As LineElement
'    Dim myprojectPoint As Point3d ' Проекция точки на сегмнет
'
'    minDistance = 500000000
'
'    myFilter.ExcludeAllTypes
'    myFilter.IncludeType msdElementTypeLineString
'    myFilter.IncludeType msdElementTypeLine
'    myFilter.IncludeType msdElementTypeComplexString
'
'        myFilter.ExcludeAllLevels
'        myFilter.IncludeLevel ActiveDesignFile.Levels.Find(UserForm_Settings.TextBox_Centreline.Text)
'
'    Set myEnum = ActiveModelReference.Scan(myFilter)
'        While myEnum.MoveNext
'            Select Case myEnum.Current.Type
'                Case msdElementTypeLineString
'                    tmpDist = DistancetoLine(myEnum.Current.AsLineElement, EndPoint)
'                    If tmpDist < minDistance Then
'                        If tmpDist > 0 Then
'                            minDistance = tmpDist
'                            Set ReCentreline = myEnum.Current.AsLineElement
'                        End If
'                    End If
'                Case msdElementTypeLine
'                    Set Mysegment = CreateLineElement2(Nothing, myEnum.Current.AsLineElement.StartPoint, myEnum.Current.AsLineElement.EndPoint)
'                    myprojectPoint = Mysegment.ProjectPointOnPerpendicular2(EndPoint, Matrix3dIdentity)
'                    tmpDist = Point3dDistanceXY(myprojectPoint, EndPoint)
'                    If tmpDist < minDistance Then
'                        If tmpDist > 0 Then
'                            minDistance = tmpDist
'                            Set ReCentreline = myEnum.Current.AsLineElement
'                        End If
'                    End If
'                Case msdElementTypeComplexString
'                    Set ComlexString = myEnum.Current.AsComplexStringElement.GetSubElements
'                        While ComlexString.MoveNext
'                            Select Case ComlexString.Current.Type
'                                Case msdElementTypeLineString
'                                    tmpDist = DistancetoLine(ComlexString.Current.AsLineElement, EndPoint)
'                                    If tmpDist < minDistance Then
'                                        If tmpDist > 0 Then
'                                            minDistance = tmpDist
'                                            Set ReCentreline = ComlexString.Current.AsLineElement
'                                        End If
'                                    End If
'                            End Select
'                        Wend
'            End Select
'        Wend
'End Sub
'
'Private Function DistancetoLine(iLine As LineElement, iPoint As Point3d) As Double
'    Dim segment As LineElement
'    Dim i As Long ' Индекс билжайшего вертекса
'    Dim projectPoint As Point3d ' Проекция точки на сегмнет
'    Dim Perp As LineElement
'
'    i = iLine.GetClosestSegment(iPoint)
'    Set segment = CreateLineElement2(Nothing, iLine.Vertex(i + 1), iLine.Vertex(i + 2))
'    projectPoint = segment.ProjectPointOnPerpendicular2(iPoint, Matrix3dIdentity)
'    DistancetoLine = Point3dDistanceXY(projectPoint, iPoint)
'
'End Function

Private Function GetLinkageId(MyEle As LineElement) As Integer
    Dim dblk() As DataBlock
    Dim name As Integer
    
    dblk = MyEle.GetUserAttributeData(attrId)
    dblk(0).CopyInteger name, False
    GetLinkageId = (name)
End Function
Private Function GetSpanByPoint(MyIndex As Long, MyVertex As Long) As String
    
    Dim i As Long
    Dim j As Long
    
    For i = 0 To UBound(Lines)
        If Lines(i).Index = MyIndex Then
            If j = MyVertex Then
                GetSpanByPoint = Lines(i).ID & "-" & Lines(i + 1).ID
                CurrentSegment = i
                Exit For
            ElseIf j <> MyVertex Then
                j = j + 1
            End If
        End If
    Next i
   ' j = 0

End Function

Private Sub Label_span_Click()
    If fixSpan = False Then
        fixSpan = True
        UserForm_General.Label_span.Font.Bold = True
    ElseIf fixSpan = True Then
        fixSpan = False
        UserForm_General.Label_span.Font.Bold = False
    End If

    
End Sub



'++++++++++++++++++++++++++++++++++++++++++++++++++++++++++++++++++++++++++++
'+++++++++++++++++++++++++++++ Домены Feature +++++++++++++++++++++++++++++++
'++++++++++++++++++++++++++++++++++++++++++++++++++++++++++++++++++++++++++++
'++++++++++++++++++++++++++++++++++++++++++++++++++++++++++++++++++++++++++++

Private Sub UserForm_Initialize()

    UserForm_General.ComboBox_Feature.AddItem "Buildings(260)"
    UserForm_General.ComboBox_Feature.AddItem "Structures(261)"
    UserForm_General.ComboBox_Feature.AddItem "Condoctor(553)"
    InitializationReference
End Sub

Private Sub ComboBox_Feature_Change()
    UserForm_General.ComboBox_Description.Clear
    Select Case UserForm_General.ComboBox_Feature.ListIndex + 1
        Case 1
            UserForm_General.ComboBox_Description.AddItem "New Building"
            UserForm_General.ComboBox_Description.AddItem "New Building + 2 m"
        Case 2
            UserForm_General.ComboBox_Description.AddItem "New str"
            UserForm_General.ComboBox_Description.AddItem "old str"
        Case 3
            UserForm_General.ComboBox_Description.AddItem "Violation"
            UserForm_General.ComboBox_Description.AddItem "Breack condactor"
    End Select
End Sub

Attribute VB_Name = "UserForm_Settings"
Attribute VB_Base = "0{74142621-DAD0-40D6-8C66-7DBF67994C16}{3C870FDA-B483-4953-BD19-58E93D17DF62}"
Attribute VB_GlobalNameSpace = False
Attribute VB_Creatable = False
Attribute VB_PredeclaredId = True
Attribute VB_Exposed = False
Attribute VB_TemplateDerived = False
Attribute VB_Customizable = False
Option Explicit


Private Sub CommandButton_loadSettigs_Click()
    LoadSettings
End Sub

Private Sub UserForm_QueryClose(Cancel As Integer, CloseMode As Integer)
    Cancel = 1
    Me.Hide
End Sub

Private Sub LoadSettings()
    Dim strFName As String
    Dim lngfhandle As Long
    Dim lngrid As Long
    Dim retVal As Long
    Dim PathPTS As String
    Dim FFile As Long
    Dim TextLine As String
    Dim XSplit() As String
    Dim i As Integer
    Dim k As Long
    Dim Settings As String
    Dim SplitSett() As String
    
    
    ReDim MyTowers(0)
    
    strFName = Space(255)
    retVal = mdlDialog_fileOpen(strFName, lngfhandle, lngrid, "", "*.txt", _
                                    ActiveDesignFile.Path, "Открыть файл с настройками")
    
    Select Case retVal
        Case 0 'Open
            PathPTS = Left(strFName, InStr(1, strFName, Chr(0)) - 1)
            FFile = FreeFile
            Open PathPTS For Input As #FFile
            While EOF(FFile) = False
                Line Input #FFile, TextLine
                XSplit = Split(TextLine, ":")
                Settings = XSplit(1)
                SplitSett = Split(Settings, ";")
                    For k = 0 To UBound(SplitSett)
                        Select Case i
                            Case 0
                                UserForm_General.ComboBox_Feature.AddItem SplitSett(k)
                            Case 1
                                UserForm_General.ComboBox_Description.AddItem SplitSett(k)
                        End Select
                    Next k
                i = i + 1
            Wend
            MsgBox "Файл координат опор загружен загружен:" & vbCr & strFName
            UserForm_General.ComboBox_Feature.ListIndex = 0
            UserForm_General.ComboBox_Description.ListIndex = 0
        Case 1 'Cancel
            MsgBox "Файл не выделен"
    End Select
    
End Sub
