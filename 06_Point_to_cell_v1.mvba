Attribute VB_Name = "Module1"
Option Explicit
Public Type ElvPoints
    mPoint As Point3d
    mLevel As Level
End Type


Public mTimeS As Date
Public mTimeE As Date

Sub Main()
MyForm.Show vbModeless
End Sub

Attribute VB_Name = "MyForm"
Attribute VB_Base = "0{7D5FEC63-DF9E-4C11-B96F-8BBD1A455576}{A296DAF6-3A48-4559-9C2C-47A1A390C5BD}"
Attribute VB_GlobalNameSpace = False
Attribute VB_Creatable = False
Attribute VB_PredeclaredId = True
Attribute VB_Exposed = False
Attribute VB_TemplateDerived = False
Attribute VB_Customizable = False
Option Explicit
Private Sub cbByLevel_Change()
    If cbByLevel.Value = True Then
        cmbLevel.Enabled = True
        LLevel.Enabled = True
    ElseIf cbByLevel.Value = False Then
        cmbLevel.Enabled = False
        LLevel.Enabled = False
    End If
End Sub
Private Sub cbxSHCell_Change()
    Dim MyCellEnum As CellInformationEnumerator
    Dim MyCell As CellInformation
    cmbCell.Clear
    Set MyCellEnum = Application.GetCellInformationEnumerator(True, False)
    While MyCellEnum.MoveNext
    Set MyCell = MyCellEnum.Current
        If cbxSHCell.Value = True Then
            If MyCell.IsShared Then cmbCell.AddItem MyCell.Name
        ElseIf cbxSHCell.Value = False And IsCellLibraryAttached And Not MyCell.IsShared Then cmbCell.AddItem MyCell.Name
        End If
    Wend
End Sub

Private Sub CheckBox_drawTxt_Change()
    If CheckBox_drawTxt.Value = True Then
        TextStyleSwitch (True)
    Else
        TextStyleSwitch (False)
    End If
End Sub

Private Sub cmbReplace_Click()
    ListBoxReport.Clear
    mTimeS = Time
    ListBoxReport.AddItem "Старт: " & Format(mTimeS, "Long Time")
    PointToCell cmbCell.Text
End Sub

Private Sub InitializeFontName(mComboBox As ComboBox)
    Dim MyModel As ModelReference
    Dim myFont As Font
    mComboBox.Clear
    Set MyModel = ActiveDesignFile.DefaultModelReference
        For Each myFont In MyModel.DesignFile.Fonts
            mComboBox.AddItem myFont.Name
        Next
 '   mComboBox.Value = mComboBox.List(0)
End Sub
Private Sub InitializeCellsAsAttach(mCmboBox As ComboBox)
    Dim MyCellEnum As CellInformationEnumerator
    Dim MyCell As CellInformation
    
    mCmboBox.Clear
        If IsCellLibraryAttached Then
            Set MyCellEnum = Application.GetCellInformationEnumerator(True, False)
            While MyCellEnum.MoveNext
                Set MyCell = MyCellEnum.Current
                If Not MyCell.IsShared Then mCmboBox.AddItem MyCell.Name
            Wend
        Else: MsgBox "Библиотека Cell не подключена", vbOKOnly
        End If
End Sub
Private Sub InitializeLevels(mComboBox As ComboBox)
    Dim myLevel As Level
    
    mComboBox.Clear
    For Each myLevel In ActiveDesignFile.Levels
      mComboBox.AddItem myLevel.Name
    Next
End Sub
Private Sub InitializeJustification(mComboBox As ComboBox)
    mComboBox.AddItem "Right Top"
    mComboBox.AddItem "Right Center"
    mComboBox.AddItem "Right Bottom"
    mComboBox.AddItem "Best Position"
    mComboBox.Value = mComboBox.List(1)
End Sub
Private Sub InitializeOffset()
    TextBoxTextOffset.Text = FormatNumber(Round(CDbl(TextBoxFontHeight.Text) * 0.25, 2), 2)
End Sub

Private Sub ComboBoxJustification_Change()
    If ComboBoxJustification.Value = "Best Position" Then
        ChangeAddLevels True
    Else
        ChangeAddLevels False
    End If
    
End Sub

Private Sub ChangeAddLevels(mValue As Boolean)
    CheckBoxAddLevels.Enabled = mValue
    CommandButtonShowLevelsList.Enabled = mValue
End Sub

Private Sub CommandButtonShowLevelsList_Click()
    UserFormLevels.InitializeLevels UserFormLevels.ListBoxLevels
    UserFormLevels.Show vbModeless
End Sub

Private Sub TextBoxFontHeight_Change()
    InitializeOffset
End Sub

Private Sub UserForm_Initialize()
    InitializeLevels cmbLevel
    InitializeCellsAsAttach cmbCell
    InitializeFontName ComboBoxFontName
    InitializeJustification ComboBoxJustification
    InitializeOffset
End Sub
Sub PointToCell(celltxt As String)
    Dim MyEnum As ElementEnumerator
    Dim i As Double
    Dim b As Integer
    Dim textBoundares() As Element
    Dim cutBound() As Element
    b = 0
    Dim tPoints() As Element
    Dim oP() As Element
    Dim mKlaster() As Element
    Dim mRange As Range3d
    
    If cbByLevel.Value = True Then
        InitializeEnum MyEnum
    ElseIf cbByLevel.Value = False Then
        Set MyEnum = ActiveModelReference.GetSelectedElements
    End If
    
    tPoints = MyEnum.BuildArrayFromContents
    ListBoxReport.AddItem "Общее количество: " & UBound(tPoints) + 1 ' Отчет количества точек
    
    For i = 0 To UBound(tPoints)
        DrawCell celltxt, tPoints(i), textBoundares
    Next i

    If CheckBox_drawTxt.Value = True Then
        If CheckBoxAddLevels.Value = True Then
            AddInitialBound textBoundares
        End If
        
        GetRange tPoints, mRange
        GetKlasters mKlaster, mRange, UBound(tPoints)
        ListBoxReport.AddItem "Кластеров: " & UBound(mKlaster) + 1 ' Кластеров
'        PlaceTextElevation textBoundares, tPoints
        For i = 0 To UBound(mKlaster)
            ListBoxReport.AddItem " Обработка кластера: " & i + 1 & " из " & UBound(mKlaster) + 1 ' Кластеров
            If i Mod 2 = 0 Then b = 1
            GetPointInsideFence tPoints, oP, mKlaster(i), b
            ListBoxReport.AddItem "     Точек в кластере: " & UBound(oP) + 1  '
            BufferFnc mKlaster(i).AsShapeElement, CDbl(TextBoxFontHeight.Text)
'            ActiveModelReference.AddElement mKlaster(i)
'            mKlaster(i).Redraw
'            mKlaster(i).Rewrite
            Set MyEnum = mKlaster(i).AsShapeElement.GetIntersectionShapesFromRegion(textBoundares, Nothing)
            cutBound = MyEnum.BuildArrayFromContents
            PlaceTextElevation cutBound, textBoundares, oP
        Next i
    End If
'    CountReport UBound(tPoints) + 1
    mTimeE = Time
    ListBoxReport.AddItem "Продолжительность: " & Format(mTimeE - mTimeS, "Long Time")
    
End Sub
Private Sub ArrayAddArray(ByRef mArray() As Point3d, AddArray() As Point3d)
    Dim i As Long
    Dim u As Long
    
    If UBound(AddArray) = -1 Then
        Exit Sub
    Else
        On Error Resume Next
        u = UBound(mArray) + 1
        If Err.Number = 9 Then
            ReDim mArray(0)
            u = 0
        End If
        Err.Clear
        For i = 0 To UBound(AddArray)
            ReDim Preserve mArray(u + i)
            mArray(u + i) = AddArray(i)
        Next i
    End If
End Sub
Private Sub BufferFnc(ByRef mFnc As ShapeElement, b As Double)
    mFnc.ModifyVertex 0, Point3dAdd(mFnc.Vertex(1), Point3dFromXYZ(-b * 4.2, -b, 0))
    mFnc.ModifyVertex 1, Point3dAdd(mFnc.Vertex(2), Point3dFromXYZ(-b * 4.2, b, 0))
    mFnc.ModifyVertex 2, Point3dAdd(mFnc.Vertex(3), Point3dFromXYZ(b * 4.2, b, 0))
    mFnc.ModifyVertex 3, Point3dAdd(mFnc.Vertex(4), Point3dFromXYZ(b * 4.2, -b, 0))
End Sub
Private Sub GetPointInsideFence(inPoints() As Element, outPoint() As Element, fnc As ShapeElement, ByRef j As Integer)
    Dim i As Long
    Erase outPoint
    For i = 0 To UBound(inPoints)
        If Point3dInPolygonXY(inPoints(i).AsLineElement.StartPoint, fnc.GetVertices) >= j Then
            RedimPreserve outPoint
            Set outPoint(UBound(outPoint)) = inPoints(i)
            j = 0
        End If
    Next i
End Sub
Private Sub GetKlasters(ByRef mK() As Element, mR As Range3d, c As Long)
    Dim i As Long
    Dim j As Long
    Dim mV(0 To 3) As Point3d
    Dim d As Long
    Dim dx As Double, dy As Double
    
    d = 1000
    dx = mR.High.X - mR.Low.X
    dy = mR.High.Y - mR.Low.Y
    i = c \ d + 1
    If dx > dy Then
        For j = 0 To i - 1
            RedimPreserve mK
            mV(0).X = mR.Low.X + j * dx / i
            mV(0).Y = mR.Low.Y
            mV(1).X = mV(0).X
            mV(1).Y = mR.High.Y
            mV(2).X = mV(0).X + dx / i
            mV(2).Y = mV(1).Y
            mV(3).X = mV(2).X
            mV(3).Y = mV(0).Y
            Set mK(j) = CreateShapeElement1(Nothing, mV)
'            ActiveModelReference.AddElement mK(j)
'            mK(j).Redraw
        Next j
    Else
        ReDim Preserve mK(i - 1)
        For j = 0 To i - 1
'            RedimPreserve mK
            mV(0).X = mR.Low.X
            mV(0).Y = mR.Low.Y + j * dy / i
            mV(1).X = mV(0).X
            mV(1).Y = mV(0).Y + dy / i
            mV(2).X = mR.High.X
            mV(2).Y = mV(1).Y
            mV(3).X = mV(2).X
            mV(3).Y = mV(0).Y
            Set mK(i - 1 - j) = CreateShapeElement1(Nothing, mV)
'            ActiveModelReference.AddElement mK(i - 1 - j)
'            mK(i - 1 - j).Redraw
        Next j
    End If
End Sub
Private Sub InitializeEnum(ByRef mEnum As ElementEnumerator)
    Dim MyFilter As New ElementScanCriteria
    
    MyFilter.ExcludeAllLevels
    MyFilter.IncludeLevel ActiveModelReference.Levels(cmbLevel.Text)
    MyFilter.ExcludeAllTypes
    MyFilter.IncludeType msdElementTypeLine
    Set mEnum = ActiveModelReference.Scan(MyFilter)
    
End Sub

Private Sub AddInitialBound(ByRef mB() As Element)
    Dim mEnum As ElementEnumerator
    Dim MyFilter As New ElementScanCriteria
    Dim i As Long
    
    MyFilter.ExcludeAllTypes
    MyFilter.ExcludeAllLevels
    
    For i = 1 To UserFormLevels.ListBoxLevels.ListCount
        If UserFormLevels.ListBoxLevels.Selected(i - 1) = True Then
           MyFilter.IncludeLevel ActiveDesignFile.Levels(UserFormLevels.ListBoxLevels.List(i - 1))
        End If
    Next i
    MyFilter.IncludeType msdElementTypeText
    
    Set mEnum = ActiveModelReference.Scan(MyFilter)
    
    While mEnum.MoveNext
        RedimPreserve mB
        Set mB(UBound(mB)) = ShapeFromText(mEnum.Current.AsTextElement)
    Wend
End Sub
Private Sub CountReport(i As Long)
    If i = 0 Or i > 4 Then
        MsgBox "Заменено " & i & " элементов", vbOKOnly
    ElseIf i > 1 And i < 5 Then
        MsgBox "Заменено " & i & " элемента", vbOKOnly
    ElseIf i = 1 Then
        MsgBox "Заменен " & i & " элемент", vbOKOnly
    End If
End Sub
Sub DrawCell(cell As String, Line As Element, ByRef mBoundary() As Element)
    Dim MyCell As CellElement
    Dim MyShCell As SharedCellElement
    Dim i As Long
'   Dim mText As TextElement
    If cbxSHCell.Value = True Then
        Set MyShCell = CreateSharedCellElement3(cell, Line.AsLineElement.StartPoint, True)
        MyShCell.Level = ActiveDesignFile.Levels(Line.Level.Name)
        ActiveModelReference.AddElement MyShCell
        MyShCell.Redraw
    ElseIf cbxSHCell.Value = False Then
        Set MyCell = CreateCellElement3(cell, Line.AsLineElement.StartPoint, True)
        MyCell.Level = ActiveDesignFile.Levels(Line.Level.Name)
        ActiveModelReference.AddElement MyCell
        MyCell.Redraw
        
        Do While MyCell.MoveToNextElement
            If MyCell.CopyCurrentElement.IsEllipseElement Then
                RedimPreserve mBoundary
                i = UBound(mBoundary)
                Set mBoundary(i) = MyCell.CopyCurrentElement
                mBoundary(i).Transform Transform3dFromMatrix3dPoint3d(Matrix3dFromScaleFactors(1, 1, 0), Point3dFromXYZ(0, 0, 0))
            End If
        Loop
'            If CheckBox_drawTxt.Value = True Then
'                AddText CStr(MyCell.Origin.Z), MyCell.Origin, Line.Level
'            End If
    End If
        If cbDelPt.Value = True Then
            ActiveModelReference.RemoveElement Line
            Line.Redraw
        End If
End Sub
Private Sub RedimPreserve(ByRef mB() As Element)
    Dim i As Long
    On Error Resume Next
    i = UBound(mB) + 1
    If Err.Number = 9 Then
        ReDim mB(0)
    Else: ReDim Preserve mB(i)
    End If
    Err.Clear
End Sub
Private Sub SetElevation(mElement As Element)
  Element.Transform Transform3dFromMatrix3dPoint3d(Matrix3dFromScaleFactors(1, 1, 0), Point3dFromXYZ(0, 0, 0))
End Sub
Private Function CreateTextElevation(mPoint As Point3d, mLevel As Level) As TextElement
    Dim mText As TextElement
    
    Set mText = CreateTextElement1(Nothing, FormatNumber(Round(mPoint.Z, CInt(TextBoxRoundText.Text)), CInt(TextBoxRoundText.Text), vbTrue, vbTrue, vbFalse), mPoint, Matrix3dIdentity)
    mText.TextStyle.Height = CDbl(TextBoxFontHeight.Text)
    mText.TextStyle.Width = CDbl(TextBoxFontWeight.Text)
    mText.TextStyle.Font = ActiveDesignFile.Fonts(ComboBoxFontName.Text)
    mText.TextStyle.Justification = msdTextJustificationLeftBottom
    mText.Level = mLevel
    
    Set CreateTextElevation = mText
    
End Function

Private Sub MovePosition(ByRef mEle As Element, tPosition As Integer, h As Double, W As Double)
    Dim offset As Double
    
    offset = CDbl(TextBoxTextOffset.Text)
    Select Case tPosition
        Case 1
            mEle.Move Point3dFromXYZ(offset, 0, 0)
        Case 2
            mEle.Move Point3dFromXYZ(0, h * -0.5, 0)
        Case 3
            mEle.Move Point3dFromXYZ(0, h * -0.5, 0)
        Case 4
            mEle.Move Point3dFromXYZ(-(2 * offset + W), h * 0.5, 0)
        Case 5
            mEle.Move Point3dFromXYZ(0, h * -0.5, 0)
    End Select
    
    mEle.Redraw
End Sub
Private Sub TextStyleSwitch(mValue As Boolean)
    ComboBoxFontName.Enabled = mValue
    ComboBoxJustification.Enabled = mValue
    TextBoxRoundText.Enabled = mValue
    TextBoxFontHeight.Enabled = mValue
    TextBoxFontWeight.Enabled = mValue
    TextBoxTextOffset.Enabled = mValue
    Label3.Enabled = mValue
    Label7.Enabled = mValue
    Label4.Enabled = mValue
    Label5.Enabled = mValue
    Label8.Enabled = mValue
    LabelM.Enabled = mValue
    LabelM2.Enabled = mValue
    LabelM3.Enabled = mValue
    LabelOffset.Enabled = mValue
    
End Sub
Private Sub PlaceTextElevation(ByRef mBounds() As Element, ByRef gBound() As Element, mPoints() As Element)
    Dim l As Long, u As Long
    Dim l1 As Long, u1 As Long
    Dim i As Long
    Dim j As Integer
    Dim sRectangle As ShapeElement
    Dim tBoundary As ShapeElement   ' Контур текста
    Dim tElev As TextElement
    Dim mEnum As ElementEnumerator
    Dim h As Double, W As Double
    Dim rIntersect() As Element
    
    Dim offset As Double
    offset = CDbl(TextBoxTextOffset.Text)
    
    h = CDbl(TextBoxFontHeight.Text)
    InitializeBoundary mBounds, mPoints, u, l
    InitializeBoundary gBound, mPoints, u1, l1
    
'    ActiveModelReference.AddElements mBounds
    RedrawAllViews
    SortingPoints mPoints
    For i = 0 To u
        
        Set tElev = CreateTextElevation(mPoints(i).AsLineElement.StartPoint, mPoints(i).Level)
        Select Case ComboBoxJustification.Value
            Case "Right Top"
                tElev.Move Point3dFromXYZ(offset, 0, 0)
            Case "Right Center"
                tElev.Move Point3dFromXYZ(offset, h * -0.5, 0)
            Case "Right Bottom"
                tElev.Move Point3dFromXYZ(offset, h * -1, 0)
            Case "Best Position"
                ReDim Preserve mBounds(l + i)
                ReDim Preserve gBound(l1 + i)
                Set tBoundary = ShapeFromText(tElev)
                W = Point3dDistance(tBoundary.Vertex(1), tBoundary.Vertex(4))
                CreateSearchShape sRectangle, mPoints(i).AsLineElement.StartPoint, W, h, offset
                Set mEnum = sRectangle.GetIntersectionShapesFromRegion(mBounds, Nothing)
                rIntersect = mEnum.BuildArrayFromContents
                For j = 1 To 5
                    MovePosition tBoundary, j, h, W
                    MovePosition tElev, j, h, W
                    Set mEnum = tBoundary.GetIntersectionShapesFromRegion(rIntersect, Nothing)
                        If getEnumeratorCount(mEnum) = 0 Then
                            Set mBounds(l + i) = tBoundary
                            Set gBound(l1 + i) = tBoundary
                            Exit For
                        End If
                    If j = 5 Then
                        Set mBounds(l + i) = tBoundary
                        Set gBound(l1 + i) = tBoundary
                    End If
                Next j
        End Select
    ActiveModelReference.AddElement tElev
    tElev.Redraw
    Erase rIntersect
    Next i
End Sub
Private Sub CreateSearchShape(ByRef sSerch As ShapeElement, pCenter As Point3d, Width As Double, h As Double, offset As Double)
    Dim mVertex(0 To 3) As Point3d
    
    mVertex(0) = Point3dFromXY(pCenter.X - offset - Width, pCenter.Y - h)
    mVertex(1) = Point3dFromXY(mVertex(0).X, pCenter.Y + h)
    mVertex(2) = Point3dFromXY(pCenter.X + offset + Width, mVertex(1).Y)
    mVertex(3) = Point3dFromXY(mVertex(2).X, mVertex(0).Y)
    
    Set sSerch = CreateShapeElement1(Nothing, mVertex)
End Sub
Private Sub LineToPoints(mLine() As Element, ByRef mPoints() As ElvPoints)
    Dim i As Long
    Dim k As Long
    
    i = UBound(mLine)
    ReDim mPoints(i)
    
    For k = 0 To i
        mPoints(k).mPoint = mLine(k).AsLineElement.StartPoint
        mPoints(k).mLevel = mLine(k).Level
    Next k
End Sub
Private Sub SortingPoints(ByRef mPoints() As Element)
    Dim i As Long, j As Long
    Dim tPoint As Element
    
    If UBound(mPoints) > 0 Then
        For i = 0 To UBound(mPoints)
            For j = 0 To UBound(mPoints)
                If j <> i Then
                    If mPoints(j).AsLineElement.StartPoint.Y <= mPoints(i).AsLineElement.StartPoint.Y Then
                        Set tPoint = mPoints(i)
                        Set mPoints(i) = mPoints(j)
                        Set mPoints(j) = tPoint
                    End If
                End If
            Next j
        Next i
    Else: Exit Sub
    End If
End Sub
Private Sub GetRange(mp() As Element, ByRef mR As Range3d) ' Определение габаритов
    Dim i As Long
    Dim Point As Point3d
    
    mR.Low = mp(0).AsLineElement.StartPoint
    mR.High = mp(0).AsLineElement.StartPoint
    
    For i = 1 To UBound(mp)
        Point = mp(i).AsLineElement.StartPoint
        If Point.Y > mR.High.Y Then
            mR.High.Y = Point.Y
        End If
        If Point.X > mR.High.X Then
            mR.High.X = Point.X
        End If
        If Point.X < mR.Low.X Then
            mR.Low.X = Point.X
        End If
        If Point.Y < mR.Low.Y Then
            mR.Low.Y = Point.Y
        End If
    Next i
End Sub
Private Sub InitializeBoundary(ByRef mB() As Element, mPoints() As Element, ByRef mU As Long, ByRef mL As Long)
    mU = UBound(mPoints)
    On Error Resume Next
    mL = UBound(mB) + 1
    If Err.Number = 9 Then
        ReDim mB(0)
        mL = 0
    End If
    Err.Clear
End Sub
Function getEnumeratorCount(oEnumerator As ElementEnumerator) As Long
    Dim count As Long
    With oEnumerator
        .Reset
        Do While .MoveNext
            count = count + 1
        Loop
        .Reset
    End With
    getEnumeratorCount = count
End Function

Private Function ShapeFromText(ByVal mText As TextElement) As ShapeElement
    Dim tRotation As Double
    Dim p(0 To 3) As Point3d
    Dim sBoundary As Range3d
    Dim mBoundary As ShapeElement
    Dim mTransform As Transform3d
    
    tRotation = GetAngleTxt(mText)
    If tRotation <> 0 Then mText.RotateAboutZ mText.Origin, 2 * Pi - tRotation 'Поворачивает текст в горизонталь
    
    sBoundary = mText.Boundary
    p(0).X = sBoundary.Low.X
    p(0).Y = sBoundary.Low.Y
    p(1).X = sBoundary.Low.X
    p(1).Y = sBoundary.High.Y
    p(2).X = sBoundary.High.X
    p(2).Y = sBoundary.High.Y
    p(3).X = sBoundary.High.X
    p(3).Y = sBoundary.Low.Y
    
    Set mBoundary = CreateShapeElement1(Nothing, p)
    
    mTransform = Transform3dFromMatrix3dAndFixedPoint3d(mText.Rotation, mText.Origin)
    mBoundary.Transform mTransform
    
    Set ShapeFromText = mBoundary
End Function
Function GetAngleTxt(mTxt As TextElement) As Double
    Dim rotationX As Double
    Dim rotationY As Double
    Dim rotationZ As Double
    Dim scaleFactor As Double
    
    If (Matrix3dIsXRotationYRotationZRotationScale(mTxt.Rotation, rotationX, rotationY, rotationZ, scaleFactor)) Then
            GetAngleTxt = rotationZ
    End If
End Function

Attribute VB_Name = "UserFormLevels"
Attribute VB_Base = "0{C96A12A3-D747-4EF2-B742-AA472D2338D5}{C279523D-7D5F-41A2-8670-13BE400A8B36}"
Attribute VB_GlobalNameSpace = False
Attribute VB_Creatable = False
Attribute VB_PredeclaredId = True
Attribute VB_Exposed = False
Attribute VB_TemplateDerived = False
Attribute VB_Customizable = False

Private Sub UserForm_Initialize()
    UserFormLevels.InitializeLevels UserFormLevels.ListBoxLevels
End Sub

Private Sub UserForm_QueryClose(Cancel As Integer, CloseMode As Integer)
   Cancel = 1
   UserFormLevels.Hide
End Sub

Sub InitializeLevels(mListBox As ListBox)
  Dim myLevel As Level

  mListBox.Clear
  For Each myLevel In ActiveDesignFile.Levels
    mListBox.AddItem myLevel.Name
  Next
End Sub
