Attribute VB_Name = "LCE_Fence"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private Fence As ShapeElement

Private Sub ILocateCommandEvents_Accept(ByVal Element As Element, point As Point3d, ByVal View As View)
    Dim pOriginX As Long    ' начальная точка X
    Dim pOriginY As Long    ' начальная точка Y
    Dim gS As Double        ' размер сетки
    Dim nX As Double
    Dim nY As Double
    Dim i As Double
    Dim j As Double
    Dim gVert(0 To 4) As Point3d
    Dim pPoint() As Point3d
    Dim grShape As ShapeElement
    Dim mText As TextElement
    Dim nT As Long
    Dim mFormat As String
          
    gS = CDbl(UserForm1.TextBox_grid_size.Text)
    
    pOriginX = Fence.Range.Low.X
    pOriginY = Fence.Range.Low.Y
        If UserForm1.CheckBox_kratno.Value = True Then
            pOriginX = (Fence.Range.Low.X \ gS) * gS
            pOriginY = (Fence.Range.Low.Y \ gS) * gS
        End If
    
    nX = ((Fence.Range.High.X - pOriginX) \ gS) + 1
    nY = ((Fence.Range.High.Y - pOriginY) \ gS) + 1
        n = 1
        
        For t = 1 To CInt(UserForm1.TextBox_razr.Text)
            mFormat = mFormat & "0"
        Next t
        For i = 0 To nY
            For j = 0 To nX
                gVert(0) = Point3dFromXYZ(pOriginX + gS * j, pOriginY + gS * i, 0)
                gVert(1) = Point3dFromXYZ(pOriginX + gS * (j + 1), pOriginY + gS * i, 0)
                gVert(2) = Point3dFromXYZ(pOriginX + gS * (j + 1), pOriginY + gS * (i + 1), 0)
                gVert(3) = Point3dFromXYZ(pOriginX + gS * j, pOriginY + gS * (i + 1), 0)
                gVert(4) = Point3dFromXYZ(pOriginX + gS * j, pOriginY + gS * i, 0)
                Set grShape = CreateShapeElement1(Nothing, gVert, msdFillModeNotFilled)
                    pPoint = Fence.AsIntersectableElement.GetIntersectionPoints(grShape, Matrix3dIdentity)
                    If UBound(pPoint) >= 0 Or Point3dInPolygonXY(grShape.Centroid, Fence.GetVertices) = 1 Then
                        grShape.Level = ActiveDesignFile.Levels.Find(UserForm1.ComboBox_Levels.Text)
                        ActiveModelReference.AddElement grShape
                        grShape.Redraw
                            If UserForm1.CheckBox_text.Value = True Then
                                Dim BlockName As String
                                If UserForm1.CheckBox_minXY Then
                                    BlockName = UserForm1.TextBox_Preffiks.Text & CStr(gVert(0).X) & "_" & CStr(gVert(0).Y)
                                Else
                                    BlockName = Format(CStr(n), mFormat)
                                End If
                                Set mText = CreateTextElement1(Nothing, BlockName, grShape.Centroid, Matrix3dIdentity)
                                mText.Level = ActiveDesignFile.Levels.Find(UserForm1.ComboBox_Levels.Text)
                                ActiveModelReference.AddElement mText
                                mText.TextStyle.Height = gS / 22
                                mText.TextStyle.Width = gS / 22
                                mText.TextStyle.Font = ActiveDesignFile.Fonts("Arial")
                                mText.TextStyle.Justification = msdTextJustificationCenterCenter
                                
                                mText.Rewrite
                                mText.Redraw
                                n = n + 1
                            End If
                    End If
            Next j
        Next i
      
End Sub

Private Sub ILocateCommandEvents_Cleanup()

End Sub

Private Sub ILocateCommandEvents_Dynamics(point As Point3d, ByVal View As View, ByVal DrawMode As MsdDrawingMode)

End Sub

Private Sub ILocateCommandEvents_LocateFailed()
'    If UserForm_Cell_to_Point.ComboBox_cell.Text = "" Then
'        MsgBox "Выберите Cell"
'    End If
End Sub

Private Sub ILocateCommandEvents_LocateFilter(ByVal Element As Element, point As Point3d, Accepted As Boolean)
Accepted = False
If Element.IsShapeElement Then 'And Element.AsCellElement.Name = UserForm_Cell_to_Point.ComboBox_cell.Text
    Accepted = True
    Set Fence = Element.AsShapeElement
    CellName = Element.AsCellElement.Name
   ' UserForm_Cell_to_Point.Label6.Caption = Element.AsCellElement.Name
End If

End Sub

Private Sub ILocateCommandEvents_LocateReset()
    CommandState.StartDefaultCommand
End Sub

Private Sub ILocateCommandEvents_Start()
    'CommandState.EnableAccuSnap
    ShowCommand "Создание нарезки"
    ShowPrompt "Укажите контур"
End Sub

Attribute VB_Name = "Module1"
Option Explicit

Sub Main()
    UserForm1.Show vbModeless
End Sub

Attribute VB_Name = "UserForm1"
Attribute VB_Base = "0{C1EA09B4-DE7F-4EDC-AD16-A53AF4AFEB0A}{7A7F4996-6C53-4BC0-A484-6EE8AA7B3B41}"
Attribute VB_GlobalNameSpace = False
Attribute VB_Creatable = False
Attribute VB_PredeclaredId = True
Attribute VB_Exposed = False
Attribute VB_TemplateDerived = False
Attribute VB_Customizable = False
Option Explicit

Private Sub CheckBox_text_Change()
    If CheckBox_text.Value = False Then
        TextBox_razr.Enabled = False
        Label2.Enabled = False
    Else
        TextBox_razr.Enabled = True
        Label2.Enabled = True
    End If

End Sub


Private Sub IniLevels()
    Dim myLevel As Level
        UserForm1.ComboBox_Levels.Clear
            For Each myLevel In ActiveDesignFile.Levels
                UserForm1.ComboBox_Levels.AddItem myLevel.Name
            Next
End Sub



Private Sub ComboBox_Levels_DblClick(ByVal Cancel As MSForms.ReturnBoolean)
    IniLevels
End Sub

Private Sub CommandButton_set_fence_Click()
    CommandState.StartLocate New LCE_Fence
End Sub



Private Sub UserForm_Initialize()
    IniLevels
End Sub
