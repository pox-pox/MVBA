Attribute VB_Name = "LCE_IdentifyType"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False



Private Const attrId As Long = 22352
Private Const attrId1 As Long = 22353

Implements ILocateCommandEvents
Private Sub ILocateCommandEvents_Accept(ByVal Element As Element, Point As Point3d, ByVal View As View)

End Sub

Private Sub ILocateCommandEvents_Cleanup()

End Sub

Private Sub ILocateCommandEvents_Dynamics(Point As Point3d, ByVal View As View, ByVal DrawMode As MsdDrawingMode)

End Sub

Private Sub ILocateCommandEvents_LocateFailed()
    UserForm1.Hide
    
End Sub

Private Sub ILocateCommandEvents_LocateFilter(ByVal Element As Element, Point As Point3d, Accepted As Boolean)
    Accepted = True
    Debug.Print TypeElementByDescription(Element.Type)
    UserForm1.Show vbModeless
    UserForm1.Label1.Caption = "Type: " & TypeElementByDescription(Element.Type)
    UserForm1.Label2.Caption = "Description: " & Element.Type
    UserForm1.Label1.Width = 100
    UserForm1.Label3.Caption = GetAtr(Element)
'    GetLinkage Element
'    GetLinkage Element
    UserForm1.SetFormPosition
'    Dim dpiX As Long, dpiY As Long
'
'    UserForm1.GetDPI dpiX, dpiY ' Определение плотности пикселей
    UserForm1.Label1.AutoSize = True
'
'    UserForm1.Top = 16 + (ActiveDesignFile.Views(1).GetPixelPosition(Point, False).Y) * 72 / dpiY
'    UserForm1.Left = (1920 + ActiveDesignFile.Views(1).GetPixelPosition(Point, False).X) * 72 / dpiX
    UserForm1.Width = UserForm1.Label1.Width
End Sub

Private Function GetAtr(mElem As Element) As String
    Dim oPH As PropertyHandler
    Set oPH = CreatePropertyHandler(mElem)
    Dim mStrings() As String
    Dim mString As String
    
    mStrings = oPH.GetAccessStrings
    ShowDisplayString oPH, mStrings(0), mString
    GetAtr = mString
End Function


Private Sub ShowDisplayString(oPH As PropertyHandler, accessString As String, mValue As String)
    On Error GoTo HandleError
    
    If Not oPH.SelectByAccessString(accessString) Then
        Debug.Print "NOT FOUND!!"
    Else
        mValue = CStr(oPH.GetValue)
        Debug.Print oPH.GetValue
    End If
    
    Exit Sub
HandleError:
    Debug.Print Err.Description
End Sub



Private Sub ILocateCommandEvents_LocateReset()

    UserForm1.Hide
End Sub

Private Sub ILocateCommandEvents_Start()

End Sub


Private Function TypeElementByDescription(Description As Integer) As String
    Select Case Description
        Case 1
            TypeElementByDescription = "CellLibraryHeader"
        Case 2
            TypeElementByDescription = "CellHeader"
        Case 3
            TypeElementByDescription = "Line"
        Case 4
            TypeElementByDescription = "LineString"
        Case 5
            TypeElementByDescription = "GroupData"
        Case 6
            TypeElementByDescription = "Shape"
        Case 7
            TypeElementByDescription = "TextNode"
        Case 8
            TypeElementByDescription = "DigSetData"
        Case 9
            TypeElementByDescription = "DesignFileHeader"
        Case 10
            TypeElementByDescription = "LevelSymbology"
        Case 11
            TypeElementByDescription = "Curve"
        Case 12
            TypeElementByDescription = "ComplexString"
        Case 13
            TypeElementByDescription = "Conic"
        Case 14
            TypeElementByDescription = "ComplexShape"
        Case 15
            TypeElementByDescription = "Ellipse"
        Case 16
            TypeElementByDescription = "Arc"
        Case 17
            TypeElementByDescription = "Text"
        Case 18
            TypeElementByDescription = "Surface"
        Case 19
            TypeElementByDescription = "Solid"
        Case 21
            TypeElementByDescription = "BsplinePole"
        Case 22
            TypeElementByDescription = "PointString"
        Case 23
            TypeElementByDescription = "Cone"
        Case 24
            TypeElementByDescription = "BsplineSurface"
        Case 25
            TypeElementByDescription = "BsplineBoundary"
        Case 26
            TypeElementByDescription = "BsplineKnot"
        Case 27
            TypeElementByDescription = "BsplineCurve"
        Case 28
            TypeElementByDescription = "BsplineWeight"
        Case 33
            TypeElementByDescription = "Dimension"
        Case 34
            TypeElementByDescription = "SharedCellDefinition"
        Case 35
            TypeElementByDescription = "SharedCell"
        Case 36
            TypeElementByDescription = "MultiLine"
        Case 37
            TypeElementByDescription = "Tag"
        Case 38
            TypeElementByDescription = "DgnStoreComponent"
        Case 39
            TypeElementByDescription = "DgnStoreHeader"
        Case 44
            TypeElementByDescription = "44"
        Case 66
            TypeElementByDescription = "MicroStation"
        Case 87
            TypeElementByDescription = "RasterHeader"
        Case 88
            TypeElementByDescription = "RasterComponent"
        Case 90
            TypeElementByDescription = "RasterReference"
        Case 91
            TypeElementByDescription = "RasterReferenceComponent"
        Case 94
            TypeElementByDescription = "RasterFrame"
        Case 95
            TypeElementByDescription = "TableEntry"
        Case 96
            TypeElementByDescription = "Table"
        Case 97
            TypeElementByDescription = "ViewGroup"
        Case 98
            TypeElementByDescription = "View"
        Case 99
            TypeElementByDescription = "LevelMask"
        Case 100
            TypeElementByDescription = "ReferenceAttachment"
        Case 101
            TypeElementByDescription = "MatrixHeader"
        Case 102
            TypeElementByDescription = "MatrixIntegerData"
        Case 103
            TypeElementByDescription = "MatrixDoubleData"
        Case 105
            TypeElementByDescription = "MeshHeader"
        Case 108
            TypeElementByDescription = "ReferenceOverride"
        Case 110
            TypeElementByDescription = "NamedGroupHeader"
        Case 111
            TypeElementByDescription = "NamedGroupComponent"
     End Select
End Function

Attribute VB_Name = "Module1"
Sub Main()
    CommandState.StartLocate New LCE_IdentifyType
End Sub

Attribute VB_Name = "UserForm1"
Attribute VB_Base = "0{7BEFA04A-1CBA-43E4-94E9-BD3A699F1DE1}{5326F088-42A0-4AE1-ADDE-29A40F0BA85B}"
Attribute VB_GlobalNameSpace = False
Attribute VB_Creatable = False
Attribute VB_PredeclaredId = True
Attribute VB_Exposed = False
Attribute VB_TemplateDerived = False
Attribute VB_Customizable = False
    '????????? ??? ??????? API
    Private Const GWL_STYLE As Long = -16& '??? ????????? ?????? ???? ????
    Private Const GWL_EXSTYLE = -20& '??? ???????????? ????? ????
    Private Const WS_CAPTION As Long = &HC00000 '?????????? ?????????
    Private Const WS_BORDER As Long = &H800000 '?????????? ????? ?????
    '??????? API, ??????????? ??? ?????? ???? ? ????????? ??? ?????

    Private Declare Function SetWindowLong Lib "User32" Alias "SetWindowLongA" (ByVal hwnd As Long, ByVal nIndex As Long, ByVal dwNewLong As Long) As Long
    Private Declare Function GetWindowLong Lib "User32" Alias "GetWindowLongA" (ByVal hwnd As Long, ByVal nIndex As Long) As Long
    Private Declare Function FindWindow Lib "user32.dll" Alias "FindWindowA" (ByVal lpClassName As String, ByVal lpWindowName As String) As Long
    Private Declare Function DrawMenuBar Lib "user32.dll" (ByVal hwnd As Long) As Long

 
 
Private Const LOGPIXELSX = 88 ' Logical pixels/inch in X
Private Const LOGPIXELSY = 90 ' Logical pixels/inch in Y


'Private Declare Function FindWindow Lib "user32" Alias "FindWindowA" (ByVal lpClassName As String, ByVal lpWindowName As String) As Long
Private Declare Sub SetWindowPos Lib "User32" (ByVal hwnd As Long, ByVal hWndInsertAfter As Long, ByVal X As Long, ByVal Y As Long, ByVal cx As Long, ByVal cy As Long, ByVal wFlags As Long)
Private Declare Function GetCursorPos Lib "User32" (lpPoint As POINTAPI) As Long
 
Private Type POINTAPI
    X As Long
    Y As Long
End Type
Private Const HWND_TOPMOST = -1
Private Const SWP_SHOWWINDOW = &H40
Private Const SWP_NOSIZE = &H1
 
Public Sub ChangeWindow(f As UserForm)
  Dim hwnd As Long
  Dim retval As Long
  hwnd = FindWindow("ThunderDFrame", f.Caption)
  If hwnd <> 0 Then
    retval = SetWindowLong(hwnd, GWL_STYLE, GetWindowLong(hwnd, GWL_STYLE) And WS_BORDER)
  End If
  If retval = 0 Then MsgBox "Fail"
End Sub
 
Private Sub UserForm_Initialize()
    Dim ihWnd, hStyle
       
    ihWnd = FindWindow("ThunderDFrame", Me.Caption) '??? Excel 2000 ? ????

    '???????? ?????????? ? ????????? ????(????? ? ?.?.)
    hStyle = GetWindowLong(ihWnd, GWL_STYLE)
    '????????? ?????????? ????? ????? ??? ???? ?????
    hStyle = hStyle And Not WS_CAPTION And Not WS_BORDER
    '???????? ??? ????: ??????? ????(?????????) ? ?????
    SetWindowLong ihWnd, GWL_STYLE, hStyle
    SetWindowLong ihWnd, GWL_EXSTYLE, 0
    '?????????????? ?????, ?????? ?????? ????(?????????)
    DrawMenuBar ihWnd
    '?????? ?????? ?????, ?.?. ??????? ???????? ????????? ????? ????? ?? ?????? ?????????
    Me.Height = Me.Height + GWL_EXSTYLE
End Sub
Sub SetFormPosition()
    Dim cursorPosition As POINTAPI
                    
    GetCursorPos cursorPosition
    SetWindowPos FindWindow(vbNullString, Me.Caption), HWND_TOPMOST, cursorPosition.X + 10, cursorPosition.Y + 10, 0, 0, SWP_SHOWWINDOW Or SWP_NOSIZE
End Sub

Sub GetDPI(ByRef mDpiX As Long, ByRef mDpiY As Long)
    Dim hDc As Long
    Dim lngRetVal As Long
         
    hDc = GetDC(0)
     
        mDpiX = GetDeviceCaps(hDc, LOGPIXELSX)
        mDpiY = GetDeviceCaps(hDc, LOGPIXELSY)
     
    mDpi = ReleaseDC(0, hDc)
End Sub
