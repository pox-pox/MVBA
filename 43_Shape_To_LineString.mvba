Attribute VB_Name = "Module1"
Sub Main()
    UserForm1.Show vbModeless
End Sub

Attribute VB_Name = "UserForm1"
Attribute VB_Base = "0{DF0DB2F4-A9F4-49F4-919E-EA89DF6DE3B8}{E9C00F4B-F2EA-4BCE-AC40-BDED4E737298}"
Attribute VB_GlobalNameSpace = False
Attribute VB_Creatable = False
Attribute VB_PredeclaredId = True
Attribute VB_Exposed = False
Attribute VB_TemplateDerived = False
Attribute VB_Customizable = False
Private Sub InitializeLevels(mComboBox As ComboBox)
    Dim myLevel As Level
    
    mComboBox.Clear
    For Each myLevel In ActiveDesignFile.Levels
        mComboBox.AddItem myLevel.Name
    Next
End Sub

Private Sub CommandButton_Run_Click()
    ShapeToLineString
End Sub

Private Sub UserForm_Initialize()
    InitializeLevels ComboBox_Levels
End Sub

Private Sub ShapeToLineString()
    Dim mEnum As ElementEnumerator
    Dim mFilter As New ElementScanCriteria
    Dim mLstring As LineElement
    
    If ActiveModelReference.AnyElementsSelected Then
        Set mEnum = ActiveModelReference.GetSelectedElements
    Else
        mFilter.ExcludeAllLevels
        mFilter.ExcludeAllTypes
        
        mFilter.IncludeLevel ActiveDesignFile.Levels.Find(ComboBox_Levels.Text)
        mFilter.IncludeType msdElementTypeShape
        mFilter.IncludeType msdElementTypeComplexShape
        
        Set mEnum = ActiveModelReference.Scan(mFilter)
    End If
        
        While mEnum.MoveNext
            Select Case mEnum.Current.Type
                Case msdElementTypeShape
                    Set mLstring = CreateLineElement1(mEnum.Current, mEnum.Current.AsShapeElement.GetVertices)
                Case msdElementTypeComplexShape
                    Set mLstring = CreateLineElement1(mEnum.Current, ComplexShapeToShape(mEnum.Current.AsComplexShapeElement).GetVertices)
            End Select
            ActiveModelReference.AddElement mLstring
            mLstring.Redraw
            ActiveModelReference.RemoveElement mEnum.Current
            mEnum.Current.Redraw
        Wend
        
End Sub

Function getEnumeratorCount(oEnumerator As ElementEnumerator) As Long
    Dim count As Long
    With oEnumerator
        .Reset
        Do While .MoveNext
            count = count + 1
        Loop
        .Reset
    End With
    getEnumeratorCount = count
End Function

Private Function ComplexShapeToShape(CShape As Element) As ShapeElement
    Dim MyEnum As ElementEnumerator
    Dim MyShape As ShapeElement
    Dim Verteces() As Point3d
    Dim i As Integer
    ReDim Verteces(0)
    If CShape.IsComplexShapeElement Then
        Set MyEnum = CShape.AsComplexShapeElement.GetSubElements
            While MyEnum.MoveNext
                For i = 0 To UBound(MyEnum.Current.AsVertexList.GetVertices)
                    Verteces(UBound(Verteces)) = MyEnum.Current.AsLineElement.Vertex(i + 1)
                    ReDim Preserve Verteces(UBound(Verteces) + 1)
                Next i
                ReDim Preserve Verteces(UBound(Verteces) - 1)
            Wend
        Set MyShape = CreateShapeElement1(CShape, Verteces, msdFillModeNotFilled)
        MyShape.IsSnappable = True
        Set ComplexShapeToShape = MyShape
    ElseIf CShape.IsShapeElement Then
        Set ComplexShapeToShape = CShape.AsShapeElement
    End If
End Function
