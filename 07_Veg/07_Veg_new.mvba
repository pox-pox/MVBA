Attribute VB_Name = "Module1"
Option Explicit
Public myRegion As ShapeElement

Sub Main()
    UserForm1.Show vbModeless
End Sub

Attribute VB_Name = "PCE_Create_region"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Implements IPrimitiveCommandEvents
Private aCandidates() As Element
Private oElement As Element
Private Sub IPrimitiveCommandEvents_Cleanup()

End Sub

Private Sub IPrimitiveCommandEvents_DataPoint(Point As Point3d, ByVal View As View)
    Dim myFilter As New ElementScanCriteria
    Dim MyEnum As ElementEnumerator
    Dim shEnum As ElementEnumerator
    Dim myReg As ComplexElement
    Dim MyShape As ShapeElement
    Dim i As Long
    
   
    myFilter.ExcludeAllTypes
    myFilter.IncludeType msdElementTypeLineString
    myFilter.IncludeType msdElementTypeShape
    myFilter.IncludeType msdElementTypeComplexShape
    myFilter.IncludeType msdElementTypeLine
    
   
    
    Set MyEnum = ActiveModelReference.Scan(myFilter)
            While MyEnum.MoveNext
            If MyEnum.Current.Level.IsDisplayedInView(ActiveDesignFile.Views.Item(1)) = True Then
                Set aCandidates(i) = MyEnum.Current
                aCandidates(i).Transform Transform3dFromMatrix3dPoint3d(Matrix3dFromScaleFactors(1, 1, 0), Point3dFromXYZ(0, 0, 0)) ' Опустить на 0
                i = i + 1
                ReDim Preserve aCandidates(i)
            End If
        Wend
    ReDim Preserve aCandidates(i - 1)

    Set oElement = GetFloodBoundary(aCandidates, Nothing, Point, , False, -1, msdFillModeNotFilled)
   ' ActiveModelReference.AddElement oElement
   ' oElement.Redraw
    If oElement Is Nothing Then MsgBox "Регион не построен", vbOKOnly
    Set myReg = oElement
    'Set shEnum = myReg.GetSubElements
       ' While shEnum.MoveNext
            Set myRegion = ComplexShapeToShape(myReg)
       ' Wend
    If UserForm1.ComboBox_Func.ListIndex = 0 Then
        UserForm1.DrawSigns myRegion, CDbl(UserForm1.TextBox1.Text)
        CommandState.StartDefaultCommand
    ElseIf UserForm1.ComboBox_Func.ListIndex = 2 Then
        Set MyShape = ComplexShapeToShape(myReg)
       ' Set MyShape = CreateShapeElement1(Nothing, myRegion.GetVertices, msdFillModeNotFilled)
        ActiveModelReference.AddElement MyShape
        MyShape.Redraw
        CommandState.StartDefaultCommand
    End If
    

End Sub

Private Sub IPrimitiveCommandEvents_Dynamics(Point As Point3d, ByVal View As View, ByVal DrawMode As MsdDrawingMode)

End Sub

Private Sub IPrimitiveCommandEvents_Keyin(ByVal Keyin As String)

End Sub

Private Sub IPrimitiveCommandEvents_Reset()
    'Myform.InputFence CDbl(Myform.tbOffset.Text), Myform.cmbCell.Text
End Sub

Private Sub IPrimitiveCommandEvents_Start()
    ReDim aCandidates(0)
End Sub
Private Function ComplexShapeToShape(CShape As Element) As ShapeElement
    Dim MyEnum As ElementEnumerator
    Dim MyShape As ShapeElement
    Dim Verteces() As Point3d
    Dim i As Integer
    ReDim Verteces(0)
    If CShape.IsComplexShapeElement Then
        Set MyEnum = CShape.AsComplexShapeElement.GetSubElements
            While MyEnum.MoveNext
                For i = 0 To UBound(MyEnum.Current.AsVertexList.GetVertices)
                    Verteces(UBound(Verteces)) = MyEnum.Current.AsLineElement.Vertex(i + 1)
                    ReDim Preserve Verteces(UBound(Verteces) + 1)
                Next i
                ReDim Preserve Verteces(UBound(Verteces) - 1)
            Wend
     '   CShape.IsSnappable = True
        Set MyShape = CreateShapeElement1(CShape, Verteces, msdFillModeNotFilled)
        MyShape.IsSnappable = True
        Set ComplexShapeToShape = MyShape
    ElseIf CShape.IsShapeElement Then
        Set ComplexShapeToShape = CShape.AsShapeElement
    End If
End Function

Attribute VB_Name = "UserForm1"
Attribute VB_Base = "0{5123FF02-7F8B-410B-8BC3-FD6776A021C2}{334D0079-AA4A-48CB-A365-3D3D6250CD88}"
Attribute VB_GlobalNameSpace = False
Attribute VB_Creatable = False
Attribute VB_PredeclaredId = True
Attribute VB_Exposed = False
Attribute VB_TemplateDerived = False
Attribute VB_Customizable = False
Private Sub InitializeCell(mComboBox As ComboBox)
    Dim MyCellEnum As CellInformationEnumerator
    Dim myCell As CellInformation
    If IsCellLibraryAttached Then
        Set MyCellEnum = Application.GetCellInformationEnumerator(False, False)
        While MyCellEnum.MoveNext
            Set myCell = MyCellEnum.Current
            mComboBox.AddItem myCell.Name
        Wend
        Else: MsgBox "Библиотека Cell не подключена", vbOKOnly
    End If
End Sub

Private Sub InitializeFunc()
    ComboBox_Func.AddItem "В замкнутом регионе"
    ComboBox_Func.AddItem "В выделенном конутре"
    ComboBox_Func.AddItem "Создать регион"
    ComboBox_Func.ListIndex = 0
End Sub

Private Sub CommandButton_CreateFnce_Click()
    CommandState.StartPrimitive New PCE_Create_region
    
End Sub

Private Sub UserForm_Initialize()
    InitializeCell ComboBox_Cell1
    InitializeCell ComboBox_Cell2
    InitializeFunc
End Sub

Sub DrawSigns(mRegion As Element, offset As Double)
    Dim Xmax As Double
    Dim Xmin As Double
    Dim Ymax As Double
    Dim Ymin As Double
    Dim DX As Double
    Dim DY As Double
    Dim k As Double
    Dim l As Double
    Dim i As Long
    Dim j As Long
    Dim Rx As Double ' Коэффециен хаотичного сдвига
    Dim Ry As Double ' Коэффециен хаотичного сдвига
    Dim aCell1() As Point3d
    Dim aCell2() As Point3d
    Dim mCell As CellElement
    ReDim aCell1(0)
    ReDim aCell2(0)
    
    Xmin = mRegion.Range.Low.X
    Ymin = mRegion.Range.Low.Y
    Xmax = mRegion.Range.High.X
    Ymax = mRegion.Range.High.Y
    
    DX = Xmax - Xmin
    DY = Ymax - Ymin
    k = DX \ offset
    l = (DY \ offset) * 2
    Rx = 0
    Ry = 0
    
        If CheckBox_Rnd.Value = True Then
            Rx = Int((Rnd * offset * 0.5) - offseet * 0.25)
            Ry = Int((Rnd * offset * 0.4) - offseet * 0.2)
        End If
        
    For i = 0 To l
        For j = 0 To k
               If (i Mod 2) > 0 Then
                    aCell1(UBound(aCell1)).X = Xmin + offset * (j + 0.75) + Rx
                    aCell1(UBound(aCell1)).Y = Ymin + offset * 0.5 * i + Ry
                    ReDim Preserve aCell1(UBound(aCell1) + 1)
               ElseIf ((i Mod 2) = 0) Or i = 0 Then
                    If (i Mod 4 = 0) Then
                        aCell2(UBound(aCell2)).X = Xmin + offset * (2 * j + 0.25) + Rx
                        aCell2(UBound(aCell2)).Y = Ymin + offset * 0.5 * i + Ry
                        aCell1(UBound(aCell1)).X = Xmin + offset * (2 * j + 1.25) + Rx
                        aCell1(UBound(aCell1)).Y = Ymin + offset * 0.5 * i + Ry
                    ElseIf i Mod 4 > 0 Then
                        aCell1(UBound(aCell1)).X = Xmin + offset * (2 * j + 0.25) + Rx
                        aCell1(UBound(aCell1)).Y = Ymin + offset * 0.5 * i + Ry
                        aCell2(UBound(aCell2)).X = Xmin + offset * (2 * j + 1.25) + Rx
                        aCell2(UBound(aCell2)).Y = Ymin + offset * 0.5 * i + Ry
                    End If
                        ReDim Preserve aCell2(UBound(aCell2) + 1)
                        ReDim Preserve aCell1(UBound(aCell1) + 1)
                    
'                    If j = 0 And (i Mod 4 = 0) Then
'                        aCell2(UBound(aCell2)).X = Xmin + offset * (j + 0.25) + Rx
'                        aCell2(UBound(aCell2)).Y = Ymin + offset * 0.5 * i + Ry
'                        ReDim Preserve aCell2(UBound(aCell2) + 1)
'                    ElseIf (j Mod 2) = 0 Then
'                        aCell2(UBound(aCell2)).X = Xmin + offset * (j + 0.25) + Rx
'                        aCell2(UBound(aCell2)).Y = Ymin + offset * 0.5 * i + Ry
'                        ReDim Preserve aCell2(UBound(aCell2) + 1)
'                    ElseIf (j Mod 2) > 0 Then
'                        aCell1(UBound(aCell1)).X = Xmin + offset * (j + 0.25) + Rx
'                        aCell1(UBound(aCell1)).Y = Ymin + offset * 0.5 * i + Ry
'                        ReDim Preserve aCell1(UBound(aCell1) + 1)
'                    End If
               End If
        Next j
    Next i
    ReDim Preserve aCell1(UBound(aCell1) - 1)
    ReDim Preserve aCell2(UBound(aCell2) - 1)
    
    For i = 0 To UBound(aCell1)
        If Point3dInPolygonXY(aCell1(i), mRegion.AsShapeElement.GetVertices) = 1 Then
            Set mCell = CreateCellElement3(ComboBox_Cell1.Text, aCell1(i), True)
            ActiveModelReference.AddElement mCell
            mCell.Redraw
        End If
    Next i
    If ComboBox_Cell2.Text <> "" Then
        For i = 0 To UBound(aCell2)
            If Point3dInPolygonXY(aCell2(i), mRegion.AsShapeElement.GetVertices) = 1 Then
                Set mCell = CreateCellElement3(ComboBox_Cell2.Text, aCell2(i), True)
                ActiveModelReference.AddElement mCell
                mCell.Redraw
            End If
        Next i
    ElseIf ComboBox_Cell2.Text = "" Then
        For i = 0 To UBound(aCell2)
            If Point3dInPolygonXY(aCell1(i), mRegion.AsShapeElement.GetVertices) = 1 Then
                Set mCell = CreateCellElement3(ComboBox_Cell1.Text, aCell1(i), True)
                ActiveModelReference.AddElement mCell
                mCell.Redraw
            End If
        Next i
    End If
End Sub
