Attribute VB_Name = "LCE_Edit"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private Const attrId As Long = 22352


Private Sub ILocateCommandEvents_Accept(ByVal Element As Element, Point As Point3d, ByVal View As View)
   ' MsgBox "rere"
    GetLinkage Element.AsLineElement
End Sub

Private Sub ILocateCommandEvents_Cleanup()

End Sub

Private Sub ILocateCommandEvents_Dynamics(Point As Point3d, ByVal View As View, ByVal DrawMode As MsdDrawingMode)

End Sub

Private Sub ILocateCommandEvents_LocateFailed()

End Sub

Private Sub ILocateCommandEvents_LocateFilter(ByVal Element As Element, Point As Point3d, Accepted As Boolean)
    Accepted = False
        If Element.Type = msdElementTypeLine Or msdElementTypeLineString Then
            Accepted = True
        End If
        
End Sub

Private Sub ILocateCommandEvents_LocateReset()

End Sub

Private Sub ILocateCommandEvents_Start()
    'CommandState.EnableAccuSnap
End Sub

Private Sub GetLinkage(MyEle As LineElement)
    Dim dblk() As DataBlock
    Dim name As Integer
    
    dblk = MyEle.GetUserAttributeData(attrId)
    dblk(0).CopyInteger name, False
    UserForm_General.TextBox_edit.Text = CStr(name)
    
End Sub

Attribute VB_Name = "LCE_SetSpan"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private Const attrId As Long = 22352

Implements ILocateCommandEvents

Private Sub ILocateCommandEvents_Accept(ByVal Element As Element, Point As Point3d, ByVal View As View)
    Dim i As Long ' Индекс билжайшего вертекса
    Dim j As Long ' Индекс оси
    Dim k As Long
    Dim l As Long
    
    
    IndexView = View.Index
    i = Element.AsLineElement.GetClosestSegment(Point)
    CurrentLine = GetLinkage(Element.AsLineElement)
    For l = 0 To CurrentLine - 1
        k = k + CounVertex(l)
    Next l
    UserForm_Forma.TextBox_Span.Text = GetSpanByPoint(CurrentLine, i)
    UserForm_General.Label_span.Caption = CurrentSegment - k + CounVertex(CurrentLine - 1) + 1 & "/" & CounVertex(CurrentLine - 1) - 1

End Sub

Private Sub ILocateCommandEvents_Cleanup()

End Sub

Private Sub ILocateCommandEvents_Dynamics(Point As Point3d, ByVal View As View, ByVal DrawMode As MsdDrawingMode)

End Sub

Private Sub ILocateCommandEvents_LocateFailed()

End Sub

Private Sub ILocateCommandEvents_LocateFilter(ByVal Element As Element, Point As Point3d, Accepted As Boolean)
    Accepted = False
        If Element.Type = msdElementTypeLine Or msdElementTypeLineString Then
            Accepted = True
            
        End If
End Sub

Private Sub ILocateCommandEvents_LocateReset()

End Sub

Private Sub ILocateCommandEvents_Start()

End Sub

Private Function GetLinkage(MyEle As LineElement) As Integer
    Dim dblk() As DataBlock
    Dim name As Integer
    
    dblk = MyEle.GetUserAttributeData(attrId)
    dblk(0).CopyInteger name, False
    GetLinkage = (name)
End Function

Private Function GetSpanByPoint(MyIndex As Long, MyVertex As Long)
    
    Dim i As Long
    Dim j As Long
    
    For i = 0 To UBound(Lines)
        If Lines(i).Index = MyIndex Then
            If j = MyVertex Then
                GetSpanByPoint = Lines(i).ID & "-" & Lines(i + 1).ID
                CurrentSegment = i
                Exit For
            ElseIf j <> MyVertex Then
                j = j + 1
            End If
        End If
    Next i
   ' j = 0

End Function

Attribute VB_Name = "Module1"
Option Explicit
Sub Main()
    UserForm_General.Show vbModeless
End Sub

Attribute VB_Name = "PCE_Place_marker"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Private Const attrId As Long = 22352

Implements IPrimitiveCommandEvents

Private Sub IPrimitiveCommandEvents_Cleanup()

End Sub

Private Sub IPrimitiveCommandEvents_DataPoint(Point As Point3d, ByVal View As View)
    Dim MyPoint As LineElement
    Set MyPoint = CreateLineElement2(Nothing, Point, Point)
    ActiveModelReference.AddElement MyPoint
    MyPoint.Redraw
    AddLinkage MyPoint

End Sub

Private Sub IPrimitiveCommandEvents_Dynamics(Point As Point3d, ByVal View As View, ByVal DrawMode As MsdDrawingMode)
    Dim MyPoint As LineElement
    Set MyPoint = CreateLineElement2(Nothing, Point, Point)
    MyPoint.Redraw DrawMode
    AddLinkage MyPoint
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
    CommandState.StartDynamics
End Sub

Private Sub AddLinkage(MyEle As Element)
    Dim dblk As New DataBlock
    dblk.CopyString UserForm_General.TextBox_description.Text, True
    MyEle.AddUserAttributeData attrId, dblk
    MyEle.Rewrite
End Sub

Attribute VB_Name = "Procedure"
Option Explicit
Declare Function mdlDialog_fileOpen Lib "stdmdlbltin.dll" (ByVal _
    fileName As String, ByVal rFileH As Long, ByVal _
    resourceId As Long, ByVal suggestedFileName As String, _
    ByVal filterString As String, ByVal defaultDirectory As String, _
    ByVal titleString As String) As Long
Public Type Centrelines
    Index As Integer
    ID As String
    X As Double
    Y As Double
    Z As Double
    Span As Double
End Type
Public Type Towers
    ID As String
    X As Double
    Y As Double
    Z As Double
End Type
Public Lines() As Centrelines
Public MyTowers() As Towers
Public XLSLoadBool As Boolean
Public PTSLoadBool As Boolean
Private Const attrId As Long = 22352
Public CurrentLine As Long
Public CurrentSegment As Long
Public IndexView As Integer
Public CounVertex() As Long


Public Sub LoadSettXLS()
    Dim strFName As String
    Dim lngfhandle As Long
    Dim lngrid As Long
    Dim retVal As Long
    Dim PathXls As String
    Dim myExcel As New Excel.Application
    Dim myWorkbook As Excel.Workbook
    Dim CurrSheet As Worksheet
    Dim curRow As Long
    Dim i As Long ' Порядковый номер Оси
    Dim j As Long ' Количество вертексов в оси
    strFName = Space(255)
    
    curRow = 3 ' Начинать поиск со сторой строки
    i = 1
    ReDim Lines(0)
    ReDim CounVertex(0)
    
    retVal = mdlDialog_fileOpen(strFName, lngfhandle, lngrid, "", "*.xls", _
                                    ActiveDesignFile.Path, "Открыть файл Specification")
    Select Case retVal
        Case 0 'Open
            PathXls = Left(strFName, InStr(1, strFName, Chr(0)) - 1)
            MsgBox "Файл Specification загружен:" & vbCr & strFName
            Set myWorkbook = myExcel.Workbooks.Open(PathXls)
            Set myExcel = Nothing
            myExcel.Quit
            Set CurrSheet = myWorkbook.Worksheets(1)
                While Not (CurrSheet.Cells(curRow, 1) = "" And CurrSheet.Cells(curRow + 1, 1) = "")
                    If CurrSheet.Cells(curRow, 1) <> "" Then
                        Lines(UBound(Lines)).Index = i
                        Lines(UBound(Lines)).ID = CurrSheet.Cells(curRow, 2)
                        Debug.Print Lines(UBound(Lines)).Index & Lines(UBound(Lines)).ID
                        j = j + 1
                    ElseIf CurrSheet.Cells(curRow, 1) = "" Then
                        i = i + 1
                        ReDim Preserve Lines(UBound(Lines) - 1)
                        CounVertex(UBound(CounVertex)) = j
                        ReDim Preserve CounVertex(UBound(CounVertex) + 1)
                        j = 0
                    End If
                ReDim Preserve Lines(UBound(Lines) + 1)
                curRow = curRow + 1
                Wend
                CounVertex(UBound(CounVertex)) = j
                'ReDim Preserve CounVertex(UBound(CounVertex) - 1)
                ReDim Preserve Lines(UBound(Lines) - 1)
                XLSLoadBool = True
                If PTSLoadBool = True Then
                    JoinCoordinates
                    XLSLoadBool = False
                End If
        Case 1 'Cancel
            MsgBox "Файл не выделен"
    End Select
End Sub

Public Sub LoadPtc()
    Dim strFName As String
    Dim lngfhandle As Long
    Dim lngrid As Long
    Dim retVal As Long
    Dim PathPTS As String
    Dim FFile As Long
    Dim TextLine As String
    Dim XSplit() As String
    
    
    ReDim MyTowers(0)
    
    strFName = Space(255)
    retVal = mdlDialog_fileOpen(strFName, lngfhandle, lngrid, "", "*.pts", _
                                    ActiveDesignFile.Path, "Открыть файл с координатами опор")
    
    Select Case retVal
        Case 0 'Open
            PathPTS = Left(strFName, InStr(1, strFName, Chr(0)) - 1)
            FFile = FreeFile
            Open PathPTS For Input As #FFile
            While EOF(FFile) = False
                Line Input #FFile, TextLine
                XSplit = Split(TextLine, vbTab)
                MyTowers(UBound(MyTowers)).ID = XSplit(0)
                MyTowers(UBound(MyTowers)).X = CDbl(XSplit(1))
                MyTowers(UBound(MyTowers)).Y = CDbl(XSplit(2))
                MyTowers(UBound(MyTowers)).Z = CDbl(XSplit(3))
                Debug.Print MyTowers(UBound(MyTowers)).ID & vbTab & MyTowers(UBound(MyTowers)).X & vbTab & MyTowers(UBound(MyTowers)).Y
                ReDim Preserve MyTowers(UBound(MyTowers) + 1)
            Wend
                ReDim Preserve MyTowers(UBound(MyTowers) - 1)
                PTSLoadBool = True
            MsgBox "Файл координат опор загружен загружен:" & vbCr & strFName
            If XLSLoadBool = True Then
                JoinCoordinates
                PTSLoadBool = False
            End If
        Case 1 'Cancel
            MsgBox "Файл не выделен"
    End Select
End Sub

Public Sub JoinCoordinates()
    Dim i As Long
    Dim j As Long
    Dim k As Long ' Счетчик сопоставленных опор
    For i = 0 To UBound(Lines)
        Debug.Print "+Lines: " & Lines(i).ID
        For j = 0 To UBound(MyTowers)
            If Lines(i).ID = MyTowers(j).ID Then
                Lines(i).X = MyTowers(j).X
                Lines(i).Y = MyTowers(j).Y
                Lines(i).Z = MyTowers(j).Z
                k = k + 1
               Debug.Print "Lines: " & Lines(i).ID
            End If
        Next j
    Next i
    MsgBox "Сопоставлено: " & k & "/" & UBound(Lines) + 1
End Sub

Public Sub DrawLines()
    Dim LVertexes() As Point3d
    Dim MyLine As LineElement
    ReDim LVertexes(0)
    Dim i As Long
    
    For i = 0 To UBound(Lines)
        If i < UBound(Lines) Then
            If Lines(i).Index = Lines(i + 1).Index Then
                LVertexes(UBound(LVertexes)).X = Lines(i).X
                LVertexes(UBound(LVertexes)).Y = Lines(i).Y
                LVertexes(UBound(LVertexes)).Z = Lines(i).Z
                ReDim Preserve LVertexes(UBound(LVertexes) + 1)
            ElseIf Lines(i).Index + 1 = Lines(i + 1).Index Then
                LVertexes(UBound(LVertexes)).X = Lines(i).X
                LVertexes(UBound(LVertexes)).Y = Lines(i).Y
                LVertexes(UBound(LVertexes)).Z = Lines(i).Z
                Set MyLine = CreateLineElement1(Nothing, LVertexes)
                MyLine.Color = Lines(i).Index
                ActiveModelReference.AddElement MyLine
                MyLine.Redraw
                AddLinkage MyLine, Lines(i).Index
                ReDim Preserve LVertexes(0)
            End If
        ElseIf i = UBound(Lines) Then
            LVertexes(UBound(LVertexes)).X = Lines(i).X
            LVertexes(UBound(LVertexes)).Y = Lines(i).Y
            LVertexes(UBound(LVertexes)).Z = Lines(i).Z
            Set MyLine = CreateLineElement1(Nothing, LVertexes)
            MyLine.Color = Lines(i).Index
            ActiveModelReference.AddElement MyLine
            MyLine.Redraw
            AddLinkage MyLine, Lines(i).Index
        End If
    Next i
End Sub

Private Sub AddLinkage(MyEle As Element, link As Integer)
    Dim dblk As New DataBlock
    
    dblk.CopyInteger link, True
    MyEle.AddUserAttributeData attrId, dblk
    MyEle.Rewrite
End Sub

Public Sub FitSpan(Line As Long, Span As Long)

    Dim pCenter As Point3d
    
    pCenter.X = (Lines(CurrentSegment).X + Lines(CurrentSegment + 1).X) * 0.5
    pCenter.Y = (Lines(CurrentSegment).Y + Lines(CurrentSegment + 1).Y) * 0.5
    pCenter.Z = (Lines(CurrentSegment).X + Lines(CurrentSegment + 1).Z) * 0.5
    ActiveDesignFile.Views(IndexView).Center = pCenter
    ActiveDesignFile.Views(IndexView).Redraw
    
End Sub

Attribute VB_Name = "UserForm_General"
Attribute VB_Base = "0{29BB9EEE-38A7-4C77-9734-616029467579}{D563281E-CA44-478E-B2C7-11C0CFF23115}"
Attribute VB_GlobalNameSpace = False
Attribute VB_Creatable = False
Attribute VB_PredeclaredId = True
Attribute VB_Exposed = False
Attribute VB_TemplateDerived = False
Attribute VB_Customizable = False
Option Explicit

Private Sub CommandButton_Draw_CLine_Click()
    Procedure.DrawLines
End Sub

Private Sub CommandButton_load_pts_Click()
    Procedure.LoadPtc
End Sub

Private Sub CommandButton_load_xls_Click()
    Procedure.LoadSettXLS
End Sub

Private Sub CommandButton_next_Line_Click()
    Dim i As Long
    Dim j As Long
    
    CurrentLine = CurrentLine + 1
    If CurrentLine > UBound(CounVertex) + 1 Then CurrentLine = 1
    
    For i = 0 To CurrentLine - 1
        j = j + CounVertex(i)
    Next i
        CurrentSegment = j - CounVertex(CurrentLine - 1)
        FitSpan CurrentLine, CurrentSegment
        UserForm_General.Label_span.Caption = CurrentSegment - j + CounVertex(CurrentLine - 1) + 1 & "/" & CounVertex(CurrentLine - 1) - 1
        UserForm_Forma.TextBox_Span.Text = Lines(CurrentSegment).ID & "-" & Lines(CurrentSegment + 1).ID
        
End Sub

Private Sub CommandButton_nextSpan_Click()
    Dim i As Long
    Dim j As Long
    For i = 0 To CurrentLine - 1
        j = j + CounVertex(i)
    Next i
'    j = j - CounVertex(CurrentLine - 1)
    If CurrentSegment < j - 2 Then
        CurrentSegment = CurrentSegment + 1
        FitSpan CurrentLine, CurrentSegment
        UserForm_General.Label_span.Caption = CurrentSegment - j + CounVertex(CurrentLine - 1) + 1 & "/" & CounVertex(CurrentLine - 1) - 1
        UserForm_Forma.TextBox_Span.Text = Lines(CurrentSegment).ID & "-" & Lines(CurrentSegment + 1).ID
    End If
End Sub

Private Sub CommandButton_previousSpan_Click()
    Dim i As Long
    Dim j As Long
    For i = 0 To CurrentLine - 1
        j = j + CounVertex(i)
    Next i
'    j = j - CounVertex(CurrentLine - 1)
    If CurrentSegment > j - CounVertex(CurrentLine - 1) Then
        CurrentSegment = CurrentSegment - 1
        FitSpan CurrentLine, CurrentSegment
        UserForm_General.Label_span.Caption = CurrentSegment - j + CounVertex(CurrentLine - 1) + 1 & "/" & CounVertex(CurrentLine - 1) - 1
    End If
End Sub

Private Sub CommandButton_Set_Line_Click()
    UserForm_Forma.Show vbModeless
    CommandState.StartLocate New LCE_SetSpan
End Sub

Private Sub CommandButton1_Click()
    CommandState.StartPrimitive New PCE_Place_marker, True
End Sub

Private Sub CommandButton2_Click()
    CommandState.StartLocate New LCE_Edit
End Sub
