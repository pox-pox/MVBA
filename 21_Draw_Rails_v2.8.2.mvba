Attribute VB_Name = "LCE_Cell_to_Line"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private FirstCell As CellElement
Private Sub ILocateCommandEvents_Accept(ByVal Element As Element, point As Point3d, ByVal View As View)
    Dim myEnum As ElementEnumerator
    Dim myFilter As New ElementScanCriteria
    Dim FirstPoint As Point3d
    Dim MyLine() As Point3d
    Dim mProf() As Element
    Dim tmpCell As CellElement
    Dim RailLine As LineElement
    
    myFilter.ExcludeAllTypes
    myFilter.IncludeType msdElementTypeCellHeader
    
    Set myEnum = ActiveModelReference.Scan(myFilter)
    While myEnum.MoveNext
        If myEnum.Current.AsCellElement.Name = CellName Then
            RedimPreserveEl mProf
            Set mProf(UBound(mProf)) = myEnum.Current.AsCellElement
        End If
    Wend
    DelInitialElement mProf, FirstCell
    ActiveModelReference.RemoveElement FirstCell
    FirstCell.Redraw
    RedimPreserveP3D MyLine
    MyLine(UBound(MyLine)) = FirstCell.Origin
    Dim i As Long
    For i = 0 To UBound(mProf)
        RedimPreserveP3D MyLine
        Set tmpCell = FindMinDistanceElement(mProf, FirstCell)
        MyLine(UBound(MyLine)) = tmpCell.Origin
        Set FirstCell = tmpCell
        
        ActiveModelReference.RemoveElement tmpCell
        tmpCell.Redraw
    Next i
    Set RailLine = CreateLineElement1(Nothing, MyLine)
    ActiveModelReference.AddElement RailLine
    RailLine.Redraw
End Sub
Private Sub RemoveElementFromModelReference(ByRef mEle As Element)
    ActiveModelReference.RemoveElement mEle
    mEle.Redraw
End Sub
Private Function FindMinDistanceElement(ByRef mAxis() As Element, ByVal mLine As CellElement) As CellElement
    Dim minDist As Double, dist As Double
    Dim m As Long
    Dim line As CellElement
    
    Set line = mAxis(0).AsCellElement
    minDist = Point3dDistance(mLine.Origin, line.Origin)
    m = 0
    For i = 0 To UBound(mAxis)
        
            Set line = mAxis(i).AsCellElement
            dist = Point3dDistance(mLine.Origin, line.Origin)
            If minDist > dist Then
                minDist = dist
                m = i
            End If
        
    Next i
    Set FindMinDistanceElement = mAxis(m).AsCellElement
    If UBound(mAxis) > 0 Then DeleteElementOfArray mAxis, m
End Function
Private Sub DelInitialElement(ByRef mArr() As Element, mLine As CellElement)
    Dim i As Long
    
    For i = 0 To UBound(mArr)
        If mLine.FilePosition = mArr(i).FilePosition Then
            DeleteElementOfArray mArr, i
            Exit For
        End If
    Next i
End Sub
Private Sub RedimPreserveEl(ByRef mB() As Element)
    Dim i As Long
    On Error Resume Next
    i = UBound(mB) + 1
    If Err.Number = 9 Then
        ReDim mB(0)
    Else: ReDim Preserve mB(i)
    End If
    Err.Clear
End Sub

Private Sub RedimPreserveP3D(ByRef mB() As Point3d)
    Dim i As Long
    On Error Resume Next
    i = UBound(mB) + 1
    If Err.Number = 9 Then
        ReDim mB(0)
    Else: ReDim Preserve mB(i)
    End If
    Err.Clear
End Sub
Private Sub DeleteElementOfArray(ByRef mArr() As Element, i As Long)
    Dim k As Long
    
    For k = i To UBound(mArr) - 1
        Set mArr(k) = mArr(k + 1)
    Next k
    ReDim Preserve mArr(UBound(mArr) - 1)
End Sub

Private Sub ILocateCommandEvents_Cleanup()

End Sub

Private Sub ILocateCommandEvents_Dynamics(point As Point3d, ByVal View As View, ByVal DrawMode As MsdDrawingMode)

End Sub

Private Sub ILocateCommandEvents_LocateFailed()
'    If UserForm_Cell_to_Point.ComboBox_cell.Text = "" Then
'        MsgBox "Выберите Cell"
'    End If
End Sub

Private Sub ILocateCommandEvents_LocateFilter(ByVal Element As Element, point As Point3d, Accepted As Boolean)
Accepted = False
If Element.IsCellElement Then 'And Element.AsCellElement.Name = UserForm_Cell_to_Point.ComboBox_cell.Text
    Accepted = True
    Set FirstCell = Element.AsCellElement
    CellName = Element.AsCellElement.Name
   ' UserForm_Cell_to_Point.Label6.Caption = Element.AsCellElement.Name
End If
ShowCommand "Cells_to_Line"
ShowPrompt "Подтвердите выделение ЛКМ"
End Sub

Private Sub ILocateCommandEvents_LocateReset()

End Sub

Private Sub ILocateCommandEvents_Start()
    'CommandState.EnableAccuSnap
    ShowCommand "Cells_to_Line"
    ShowPrompt "Укажите начальный Cell"
End Sub

Attribute VB_Name = "LCE_Line_Snap"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private mElement As Element
Private Join As Boolean
Private okPoint As Point3d



Private Sub ILocateCommandEvents_Accept(ByVal Element As Element, point As Point3d, ByVal View As View)
    Dim mPoint As LineElement
    Dim prPoint As Point3d
    Dim k As Long
    
    Dim myEnum As ElementEnumerator
    Dim myFilter As New ElementScanCriteria
    Dim myComplexString() As Element
    
    myFilter.ExcludeAllTypes
    myFilter.IncludeType msdElementTypeLineString
    myFilter.IncludeType msdElementTypeComplexString
    myFilter.IncludeOnlyVisible
    
    If UserForm_Settings.CheckBox_useLevel.Value = True Then
        myFilter.ExcludeAllLevels
        For k = 1 To UserForm_Settings.ListBox_levels.ListCount
            If UserForm_Settings.ListBox_levels.Selected(k - 1) Then
                myFilter.IncludeLevel ActiveDesignFile.Levels.Find(UserForm_Settings.ListBox_levels.List(k - 1))
            End If
        Next k
    End If
    
    prPoint = Project_Point1(Element, point)
    okPoint = prPoint
    Join = False
    Set myEnum = ActiveModelReference.Scan(myFilter)
        While myEnum.MoveNext
            Select Case myEnum.Current.Type
                Case msdElementTypeLineString
                    If Point3dDistanceXY(prPoint, myEnum.Current.AsLineElement.startPoint) <= CDbl(UserForm_Settings.TextBox_searhRadius.Text) Then
                        myEnum.Current.AsLineElement.ModifyVertex 0, prPoint
                        myEnum.Current.AsLineElement.Rewrite
                        myEnum.Current.AsLineElement.Redraw
                        Join = True
                    ElseIf Point3dDistanceXY(prPoint, myEnum.Current.AsLineElement.EndPoint) <= CDbl(UserForm_Settings.TextBox_searhRadius.Text) Then
                        myEnum.Current.AsLineElement.ModifyVertex (myEnum.Current.AsLineElement.VerticesCount - 1), prPoint
                        myEnum.Current.AsLineElement.Rewrite
                        myEnum.Current.AsLineElement.Redraw
                        Join = True
                    End If
                Case msdElementTypeComplexString
                    myComplexString = myEnum.Current.AsComplexStringElement.GetSubElements.BuildArrayFromContents
                        Select Case myComplexString(0).Type
                            Case msdElementTypeLineString
                                If Point3dDistanceXY(myComplexString(0).AsLineElement.startPoint, prPoint) <= CDbl(UserForm_Settings.TextBox_searhRadius.Text) Then
                                    myComplexString(0).AsLineElement.ModifyVertex 0, prPoint
                                    myComplexString(0).AsLineElement.Rewrite
                                    myComplexString(0).AsLineElement.Redraw
                                    Join = True
                                End If
                            Case msdElementTypeLine
                                If Point3dDistanceXY(myComplexString(0).AsLineElement.startPoint, prPoint) <= CDbl(UserForm_Settings.TextBox_searhRadius.Text) Then
                                    myComplexString(0).AsLineElement.ModifyVertex 0, prPoint
                                    myComplexString(0).AsLineElement.Rewrite
                                    myComplexString(0).AsLineElement.Redraw
                                    Join = True
                                End If
                        End Select
                        
                        Select Case myComplexString(UBound(myComplexString)).Type
                            Case msdElementTypeLineString
                                If Point3dDistanceXY(myComplexString(UBound(myComplexString)).AsLineElement.EndPoint, prPoint) <= CDbl(UserForm_Settings.TextBox_searhRadius.Text) Then
                                    myComplexString(UBound(myComplexString)).AsLineElement.ModifyVertex (myComplexString(UBound(myComplexString)).AsLineElement.VerticesCount - 1), prPoint
                                    myComplexString(UBound(myComplexString)).AsLineElement.Rewrite
                                    myComplexString(UBound(myComplexString)).AsLineElement.Redraw
                                    Join = True
                                End If
                            Case msdElementTypeLine
                                If Point3dDistanceXY(myComplexString(UBound(myComplexString)).AsLineElement.EndPoint, prPoint) <= CDbl(UserForm_Settings.TextBox_searhRadius.Text) Then
                                    myComplexString(UBound(myComplexString)).AsLineElement.ModifyVertex (myComplexString(UBound(myComplexString)).AsLineElement.VerticesCount - 1), prPoint
                                    myComplexString(UBound(myComplexString)).AsLineElement.Rewrite
                                    myComplexString(UBound(myComplexString)).AsLineElement.Redraw
                                    Join = True
                                End If
                        End Select
            End Select
        Wend
    
'    Set mPoint = CreateLineElement2(Nothing, prPoint, prPoint)
'    ActiveModelReference.AddElement mPoint
'    mPoint.Redraw
If Join = False Then
    CommandState.StopDynamics
End If
End Sub

Private Sub ILocateCommandEvents_Cleanup()

End Sub

Private Sub ILocateCommandEvents_Dynamics(point As Point3d, ByVal View As View, ByVal DrawMode As MsdDrawingMode)
    Dim prPoint As Point3d
    Dim perpend As LineElement
    Dim jOk As TextElement
    
    
    If Join = False Then
        prPoint = Project_Point1(mElement, point)
        Set perpend = CreateLineElement2(Nothing, point, prPoint)
        perpend.LineWeight = 0
        perpend.Color = 4
        perpend.Redraw DrawMode
    ElseIf Join = True Then
        Set jOk = CreateTextElement1(Nothing, "OK", okPoint, Matrix3dIdentity)
        jOk.TextStyle.Height = 0.1
        jOk.TextStyle.Width = 0.1
        jOk.Redraw DrawMode
    End If
    
End Sub

Private Sub ILocateCommandEvents_LocateFailed()

End Sub

Private Sub ILocateCommandEvents_LocateFilter(ByVal Element As Element, point As Point3d, Accepted As Boolean)
Dim k As Long
Accepted = False
    If Element.IsLineElement Or Element.IsComplexElement Then
        If UserForm_Settings.CheckBox_useLevel.Value = False Then
            Accepted = True
            Set mElement = Element
            CommandState.StartDynamics
            Join = False
        ElseIf UserForm_Settings.CheckBox_useLevel.Value = True Then
            For k = 1 To UserForm_Settings.ListBox_levels.ListCount
                If UserForm_Settings.ListBox_levels.Selected(k - 1) Then
                    If Element.Level.Name = UserForm_Settings.ListBox_levels.List(k - 1) Then
                        Accepted = True
                        Set mElement = Element
                        CommandState.StartDynamics
                        Join = False
                    End If
                End If
            Next k
        End If
    End If
End Sub

Private Sub ILocateCommandEvents_LocateReset()
    CommandState.StopDynamics
    CommandState.StartDefaultCommand
End Sub

Private Sub ILocateCommandEvents_Start()
    ShowCommand "Snap"
    ShowPrompt "Укажите ось"

End Sub

Private Function Project_Point1(mLine As Element, mPoint As Point3d) As Point3d
   
Dim mComplexStr As ElementEnumerator
Dim i As Long
Dim j As Long
Dim minDist As Double
Dim tmpDist As Double
Dim tmpP As Point3d

    Select Case mLine.Type
        Case msdElementTypeLineString
            minDist = 500000
                tmpP = mPoint
                i = mLine.AsLineElement.GetClosestSegment(tmpP)
                tmpP.Z = mLine.AsLineElement.Vertex(i + 1).Z * 0.5 + mLine.AsLineElement.Vertex(i + 2).Z * 0.5

                tmpDist = Dist_Segment_to_Point(mLine.AsLineElement.Vertex(i + 1), mLine.AsLineElement.Vertex(i + 2), tmpP)
                    If tmpDist < minDist Then
                        minDist = tmpDist
                        Project_Point1 = Project_Point(mLine.AsLineElement.Vertex(i + 1), mLine.AsLineElement.Vertex(i + 2), tmpP)
                    End If
        Case msdElementTypeComplexString
            Set mComplexStr = mLine.AsComplexStringElement.GetSubElements
                minDist = 5000000
                While mComplexStr.MoveNext
                    Select Case mComplexStr.Current.Type
                        Case msdElementTypeLineString
                            tmpP = mPoint
                            i = mComplexStr.Current.AsLineElement.GetClosestSegment(tmpP)
                            tmpP.Z = mComplexStr.Current.AsLineElement.Vertex(i + 1).Z * 0.5 + mComplexStr.Current.AsLineElement.Vertex(i + 2).Z * 0.5
                            tmpDist = Dist_Segment_to_Point(mComplexStr.Current.AsLineElement.Vertex(i + 1), mComplexStr.Current.AsLineElement.Vertex(i + 2), tmpP)
                                If tmpDist < minDist Then
                                    minDist = tmpDist
                                    Project_Point1 = Project_Point(mComplexStr.Current.AsLineElement.Vertex(i + 1), mComplexStr.Current.AsLineElement.Vertex(i + 2), tmpP)
                                End If
                        Case msdElementTypeLine
                            tmpP = mPoint
                            tmpP.Z = mComplexStr.Current.AsLineElement.startPoint.Z
                            tmpDist = Dist_Segment_to_Point(mComplexStr.Current.AsLineElement.startPoint, mComplexStr.Current.AsLineElement.EndPoint, tmpP)
                                If tmpDist < minDist Then
                                minDist = tmpDist
                                Project_Point1 = Project_Point(mComplexStr.Current.AsLineElement.startPoint, mComplexStr.Current.AsLineElement.EndPoint, tmpP)
                            End If
                    End Select
                Wend
    End Select
End Function
Private Function Dist_Segment_to_Point(startPoint As Point3d, EndPoint As Point3d, iPoint As Point3d) As Double
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    Dim tmpL As LineElement
    vPoint = Vector3dSubtractPoint3dPoint3d(iPoint, startPoint)
    vLine = Vector3dSubtractPoint3dPoint3d(EndPoint, startPoint)
    
    c1 = Vector3dDotProduct(vPoint, vLine)
    c2 = Vector3dDotProduct(vLine, vLine)
        If c1 <= 0 Then
            Dist_Segment_to_Point = Point3dDistance(startPoint, iPoint)
'            Set tmpL = CreateLineElement2(Nothing, StartPoint, iPoint)
'            ActiveModelReference.AddElement tmpL
'            tmpL.Redraw
        ElseIf c2 <= c1 Then
            Dist_Segment_to_Point = Point3dDistance(EndPoint, iPoint)
'            Set tmpL = CreateLineElement2(Nothing, EndPoint, iPoint)
'            ActiveModelReference.AddElement tmpL
'            tmpL.Redraw
        Else
            k = c1 / c2
            vProject = Vector3dScale(vLine, k)
            pProject = Vector3dAdd(Vector3dFromPoint3d(startPoint), vProject)
            Dist_Segment_to_Point = Point3dDistance(Point3dFromVector3d(pProject), iPoint)
'            Set tmpL = CreateLineElement2(Nothing, Point3dFromVector3d(pProject), iPoint)
'            ActiveModelReference.AddElement tmpL
'            tmpL.Redraw
        End If
End Function
Private Function Project_Point(startPoint As Point3d, EndPoint As Point3d, iPoint As Point3d) As Point3d
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    
    vPoint = Vector3dSubtractPoint3dPoint3d(iPoint, startPoint)
    vLine = Vector3dSubtractPoint3dPoint3d(EndPoint, startPoint)
    
    c1 = Vector3dDotProduct(vPoint, vLine)
    c2 = Vector3dDotProduct(vLine, vLine)
        If c1 <= 0 Then
            Project_Point = startPoint
        ElseIf c2 <= c1 Then
            Project_Point = EndPoint
        Else
            k = c1 / c2
            vProject = Vector3dScale(vLine, k)
            Project_Point = Point3dFromVector3d(Vector3dAdd(Vector3dFromPoint3d(startPoint), vProject))
        End If
End Function

Function GetClosestSegment3d(iLine As LineElement, iPoint As Point3d) As Point3d()
    Dim i As Long
    Dim Segment(0 To 1) As Point3d ' 0 - start , 1 - end
    i = iLine.GetClosestVertex(iPoint)
        If i = 0 Then
            Segment(0) = iLine.Vertex(1)
            Segment(1) = iLine.Vertex(2)
        ElseIf i = (iLine.VerticesCount - 1) Then
            Segment(0) = iLine.Vertex((iLine.VerticesCount) - 1)
            Segment(1) = iLine.Vertex(iLine.VerticesCount)
        Else
            i = i + 1
            If Dist_Segment_to_Point(iLine.Vertex(i), iLine.Vertex(i + 1), iPoint) >= Dist_Segment_to_Point(iLine.Vertex(i - 1), iLine.Vertex(i), iPoint) Then
                Segment(0) = iLine.Vertex(i - 1)
                Segment(1) = iLine.Vertex(i)
            Else
                Segment(0) = iLine.Vertex(i)
                Segment(1) = iLine.Vertex(i + 1)
            End If
        End If
    GetClosestSegment3d = Segment
    
End Function

Attribute VB_Name = "Module1"
Public CellName As String
Public RailAdd As Integer
Sub Main()
    UserForm_Cell_to_Point.Show vbModeless
End Sub

Attribute VB_Name = "PCE_Edit"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents

Private Sub IPrimitiveCommandEvents_Cleanup()

End Sub

Private Sub IPrimitiveCommandEvents_DataPoint(point As Point3d, ByVal View As View)
    Dim myPoint As LineElement
    FindNerstVertex point
End Sub

Private Sub IPrimitiveCommandEvents_Dynamics(point As Point3d, ByVal View As View, ByVal DrawMode As MsdDrawingMode)
Dim rotation As Matrix3d
Dim transform As Transform3d
Dim myProfil As CellElement

rotation = Matrix3dInverse(View.rotation)
Set myProfil = CreateCellElement3(ActiveSettings.CellName, point, True)
transform = Transform3dFromMatrix3dAndFixedPoint3d(rotation, myProfil.Origin)
myProfil.transform transform
myProfil.Redraw DrawMode

End Sub

Private Sub IPrimitiveCommandEvents_Keyin(ByVal Keyin As String)

End Sub

Private Sub IPrimitiveCommandEvents_Reset()
    CommandState.StartDefaultCommand
End Sub

Private Sub IPrimitiveCommandEvents_Start()
    CommandState.StartDynamics
End Sub

Private Sub FindNerstVertex(EndPoint As Point3d)
    Dim myEnum As ElementEnumerator
    Dim ComlexString As ElementEnumerator
    Dim myFilter As New ElementScanCriteria
    Dim i As Long
    Dim Rail As LineElement
    Dim minDistance As Double
    Dim tLineString As LineElement
    Dim j As Long
    Dim o As Long
    Dim movePoint As Point3d
    Dim tmpDist As Double
    
    
    minDistance = CDbl(UserForm_Settings.TextBox_tolerance.Text)
    
    myFilter.ExcludeAllTypes
    myFilter.IncludeType msdElementTypeLineString
    myFilter.IncludeType msdElementTypeComplexString
    
    If UserForm_Settings.TextBox_tolerance.Text <> "" Then
        myFilter.ExcludeAllLevels
        myFilter.IncludeLevel ActiveDesignFile.Levels.Find(UserForm_Settings.ComboBox_edit.Text)
    End If
        
    Set myEnum = ActiveModelReference.Scan(myFilter)
        While myEnum.MoveNext
            Select Case myEnum.Current.Type
                Case msdElementTypeLineString
                    tmpDist = DistancetoLine(myEnum.Current.AsLineElement, EndPoint)
                    If tmpDist < minDistance Then
                        If tmpDist > 0 Then
                            minDistance = tmpDist
                            Set Rail = myEnum.Current.AsLineElement
                        End If
                    End If
                Case msdElementTypeComplexString
                    Set ComlexString = myEnum.Current.AsComplexStringElement.GetSubElements
                        While ComlexString.MoveNext
                            Select Case ComlexString.Current.Type
                                Case msdElementTypeLineString
                                    tmpDist = DistancetoLine(ComlexString.Current.AsLineElement, EndPoint)
                                    If tmpDist < minDistance Then
                                        If tmpDist > 0 Then
                                            minDistance = tmpDist
                                            Set Rail = ComlexString.Current.AsLineElement
                                        End If
                                    End If
                            End Select
                        Wend
            End Select
        Wend
    If RailAdd = 1 Then
        InsertVertex Rail, EndPoint
    ElseIf RailAdd = 0 Then
        j = Rail.GetClosestVertex(EndPoint)
        Rail.ModifyVertex j, EndPoint
        Rail.Rewrite
        Rail.Redraw
    End If
End Sub

Private Function DistancetoLine(iLine As LineElement, iPoint As Point3d) As Double

    Dim vPoint As Vector3d
    Dim vLine As Vector3d
    Dim vProject As Vector3d
    Dim i As Long ' Индекс билжайшего вертекса
    Dim Segment As LineElement
    Dim ax As Double
    Dim ay As Double
    Dim az As Double
    Dim c1 As Double 'Скалярное произведение vPoint x vLine
    Dim c2 As Double 'Скалярное произведение vline x vLine
    Dim k As Double ' Коэффециент проекции
    Dim pProject As Point3d
    
    i = iLine.GetClosestSegment(iPoint)
    Set Segment = CreateLineElement2(Nothing, iLine.Vertex(i + 1), iLine.Vertex(i + 2))
    
    ax = iPoint.X - Segment.startPoint.X
    ay = iPoint.Y - Segment.startPoint.Y
    az = iPoint.Z - Segment.startPoint.Z
    
    vPoint = Vector3dFromXYZ(ax, ay, az)
    
    ax = Segment.EndPoint.X - Segment.startPoint.X
    ay = Segment.EndPoint.Y - Segment.startPoint.Y
    az = Segment.EndPoint.Z - Segment.startPoint.Z
    
    vLine = Vector3dFromXYZ(ax, ay, az)
    
    c1 = Vector3dDotProduct(vPoint, vLine)
    c2 = Vector3dDotProduct(vLine, vLine)
    
        If c1 <= 0 Then
            DistancetoLine = Point3dDistance(Segment.startPoint, iPoint)
        ElseIf c2 <= c1 Then
            DistancetoLine = Point3dDistance(Segment.EndPoint, iPoint)
        ElseIf c1 = Segment.Length * Point3dDistance(iPoint, Segment.startPoint) Then
            DistancetoLine = Point3dDistance(iPoint, iPoint)
        Else
            k = c1 / c2
            vProject = Vector3dScale(vLine, k)
            pProject.X = Segment.startPoint.X + vProject.X
            pProject.Y = Segment.startPoint.Y + vProject.Y
            pProject.Z = Segment.startPoint.Z + vProject.Z
            DistancetoLine = Point3dDistance(pProject, iPoint)
        End If
    
'    Dim segment As LineElement
'    Dim i As Long ' Индекс билжайшего вертекса
'    Dim projectPoint As Point3d ' Проекция точки на сегмнет
'    Dim Perp As LineElement
'    Dim myPoint As LineElement
'
'    Set myPoint = CreateLineElement2(Nothing, iPoint, iPoint)
'    myPoint.Color = 3
'    myPoint.LineWeight = 8
'    ActiveModelReference.AddElement myPoint
'    myPoint.Redraw
'
'    i = iLine.GetClosestSegment(iPoint)
'        Set segment = CreateLineElement2(Nothing, iLine.Vertex(i + 1), iLine.Vertex(i + 2))
'        segment.Color = 3
'        segment.LineWeight = 4
'        ActiveModelReference.AddElement segment
'        projectPoint = segment.ProjectPointOnPerpendicular2(iPoint, Matrix3dIdentity)
'        DistancetoLine = Point3dDistance(projectPoint, iPoint)


End Function

Private Sub InsertVertex(iLine As LineElement, iPoint As Point3d)
    Dim i As Long
    i = iLine.GetClosestSegment(iPoint)
    iLine.InsertVertex i + 1, iPoint
    iLine.Rewrite
    iLine.Redraw
    
End Sub

Attribute VB_Name = "UserForm_Cell_to_Point"
Attribute VB_Base = "0{9AA76556-CBEF-4CEA-B8B8-232D11FF4488}{EB67BF9B-7198-4616-9818-8FDFDFEEC73E}"
Attribute VB_GlobalNameSpace = False
Attribute VB_Creatable = False
Attribute VB_PredeclaredId = True
Attribute VB_Exposed = False
Attribute VB_TemplateDerived = False
Attribute VB_Customizable = False

Private Sub CommandButton_cell_to_line_Click()
    CommandState.StartLocate New LCE_Cell_to_Line
End Sub

Private Sub CommandButton_cie_Click()
    CommandButton_cie.Visible = False
    HookKey
End Sub

Private Sub CommandButton_connect_Click()
    CommandState.StartLocate New LCE_Line_Snap
End Sub

Private Sub CommandButton_draw_point_Click()
    DrawPoint
End Sub

Private Sub CommandButton_edit_Click()
    CommandState.StartPrimitive New PCE_Edit, True
End Sub

Private Sub CommandButton_Rail_Add_Click()
    RailAdd = 1
    CommandState.StartPrimitive New PCE_Edit, True
End Sub

Private Sub CommandButton_Rail_L_Click()
    ActiveSettings.CellName = UserForm_Settings.ComboBox_Rail_Left.Text
    CadInputQueue.SendCommand "DIALOG CELLMAINTENANCE"
    CadInputQueue.SendCommand "PLACE CELL ICON"
End Sub

Private Sub CommandButton_Rail_move_Click()
    RailAdd = 0
    CommandState.StartPrimitive New PCE_Edit, True
End Sub

Private Sub CommandButton_Rail_R_Click()
    ActiveSettings.CellName = UserForm_Settings.ComboBox_Rail_Right.Text
    CadInputQueue.SendCommand "DIALOG CELLMAINTENANCE"
    CadInputQueue.SendCommand "PLACE CELL ICON"
End Sub

Private Sub CommandButton1_Click()
On Error Resume Next
    IModalDialogEvents_OnDialogOpened "Travel Path", msdDialogBoxResultOK
    CadInputQueue.SendKeyin "Travel path"
End Sub
Private Sub IModalDialogEvents_OnDialogOpened(ByVal DialogBoxName As String, DialogResult As MsdDialogBoxResult)

    If DialogBoxName = "Travel Path" Then

    '   Set a variable associated with a dialog box
        SetCExpressionValue "FlyDepth", 0.5, "TSCAN"
        SetCExpressionValue "FlyWidth", 0.5, "TSCAN"
        SetCExpressionValue "FlyDepth", 0.3, "TSCAN"
        SetCExpressionValue "FlyDoTop", -1, "TSCAN"

        SetCExpressionValue "FlyTopView", 0, "TSCAN"
        SetCExpressionValue "FlyCrossView", 1, "TSCAN"
        SetCExpressionValue "FlyFixRange", 2, "TSCAN"

        SetCExpressionValue "FlyMinDz", -0.05, "TSCAN"
        SetCExpressionValue "FlyMaxDz", 0.1, "TSCAN"
    '   Remove the following line to let the user close the dialog box.
      '  DialogResult = msdDialogBoxResultOK

    End If  ' Travel Path

End Sub
Private Sub CommandButton_Settings_Click()
    UserForm_Settings.Show vbModeless
End Sub
Private Sub UserForm_Initialize()
    UserFormIni
    IniLevels
End Sub
Private Sub UserFormIni()
    Dim myLevel As Level
    UserForm_Settings.ComboBox_level_line.Clear
    UserForm_Settings.ComboBox_level_point.Clear
    UserForm_Settings.ComboBox_edit.Clear
            For Each myLevel In ActiveModelReference.Levels
                UserForm_Settings.ComboBox_level_line.AddItem myLevel.Name
                UserForm_Settings.ComboBox_level_point.AddItem myLevel.Name
                UserForm_Settings.ComboBox_edit.AddItem myLevel.Name
            Next
 End Sub
 Private Sub IniLevels()
    Dim myLevel As Level
        UserForm_Settings.cmbLevels.Clear
            For Each myLevel In ActiveDesignFile.Levels
                UserForm_Settings.cmbLevels.AddItem myLevel.Name
            Next
End Sub


Sub HookKey()
    Dim oMessage As CadInputMessage
    Dim rotation As Matrix3d
    Dim transform As Transform3d
    Dim MyCell As CellElement
    On Error GoTo exitCIQ
        Do While True
            Set oMessage = CadInputQueue.GetInput
            Select Case oMessage.InputType
                Case msdCadInputTypeDataPoint
                    CadInputQueue.SendDataPoint oMessage.point
                    CadInputQueue.SendKeyin "Travel step forward"
                    ActiveDesignFile.Views(oMessage.View.Index).Redraw
                    rotation = Matrix3dInverse(oMessage.View.rotation)
                    Set MyCell = ActiveModelReference.GraphicalElementCache.GetLastValidElement.AsCellElement
                    transform = Transform3dFromMatrix3dAndFixedPoint3d(rotation, MyCell.Origin)
                    MyCell.transform transform
                    MyCell.Rewrite
                Case msdCadInputTypeKeyin
                    CadInputQueue.SendKeyin oMessage.Keyin
                Case msdCadInputTypeReset
                    CadInputQueue.SendReset
                    CommandButton_cie.Visible = True
                    Exit Do
            End Select
        Loop
exitCIQ:
End Sub

Private Sub DrawPoint()
    Dim myEnum              As ElementEnumerator
    Dim InsideEnum          As ElementEnumerator
    Dim ComplexString       As ElementEnumerator
    Dim myFilter            As New ElementScanCriteria
    Dim aLine()             As Element
    Dim lComplex()          As Element
    Dim l                   As Long
    Dim pIntersection()     As Point3d
    Dim i                   As Long
    Dim k                   As Long
    Dim j                   As Long
    Dim count               As Long
    Dim pStart              As Point3d
    Dim pEnd                As Point3d
    Dim pSwitch             As LineElement
    Dim currentLine         As Element
    Dim complex             As ElementEnumerator
    Dim first               As Boolean
    myFilter.ExcludeAllTypes
    myFilter.ExcludeAllLevels
    
    myFilter.IncludeLevel ActiveDesignFile.Levels(UserForm_Settings.ComboBox_level_line.Text)
    myFilter.IncludeType msdElementTypeLineString
    myFilter.IncludeType msdElementTypeComplexString
    
    Set myEnum = ActiveModelReference.Scan(myFilter)
    aLine() = myEnum.BuildArrayFromContents
    
    For i = 0 To UBound(aLine)
        Select Case aLine(i).Type
            Case msdElementTypeLineString
                pStart = aLine(i).AsLineElement.startPoint
                pEnd = aLine(i).AsLineElement.EndPoint
            Case msdElementTypeComplexString
                pStart = aLine(i).AsComplexStringElement.startPoint
                pEnd = aLine(i).AsComplexStringElement.EndPoint
        End Select
        For k = 0 To UBound(aLine)
            If k <> i Then
                Select Case aLine(k).Type
                    Case msdElementTypeLineString
                        If DistancetoLine(aLine(k).AsLineElement, pEnd) = 0 Then
                            PlacePoint pEnd
                            count = count + 1
                        End If
                        If DistancetoLine(aLine(k).AsLineElement, pStart) = 0 Then
                            PlacePoint pStart
                            count = count + 1
                        End If
                    Case msdElementTypeComplexString
                       ' lComplex = aLine(k).AsComplexStringElement.GetSubElements.BuildArrayFromContents
                        Set complex = aLine(k).AsComplexStringElement.GetSubElements
                        lComplex() = complex.BuildArrayFromContents
                       ' While complex.MoveNext
                        For l = 0 To UBound(lComplex)
                         
                            Select Case lComplex(l).Type
                                Case msdElementTypeLineString
                                
                                    If DistancetoLine(lComplex(l).AsLineElement, pStart) = 0 Then
                                        If l = 0 Then
                                            PlacePoint pStart
                                            count = count + 1
                                        End If
                                        If l > 0 Then
                                            If DistancetoLine(lComplex(l).AsLineElement, pStart) <> DistancetoLine(lComplex(l - 1).AsLineElement, pStart) Then
                                                PlacePoint pStart
                                                count = count + 1
                                            End If
                                        End If
                                        
                                            
                                    End If
                                    If DistancetoLine(lComplex(l).AsLineElement, pEnd) = 0 Then
                                        If l = 0 Then
                                            PlacePoint pEnd
                                            count = count + 1
                                        End If
                                        If l > 0 Then
                                            If DistancetoLine(lComplex(l).AsLineElement, pEnd) <> DistancetoLine(lComplex(l - 1).AsLineElement, pEnd) Then
                                                PlacePoint pEnd
                                                count = count + 1
                                            End If
                                        End If
                                        
                                    End If
                                    
                            End Select
                        Next l
                        'Wend
                End Select
            End If
        Next k
    Next i
        

MsgBox "Создано точек: " & count
End Sub

Function DistancetoLine(iLine As LineElement, iPoint As Point3d) As Double

    Dim Segment         As LineElement
    Dim i               As Long ' Индекс билжайшего вертекса
    Dim projectPoint    As Point3d ' Проекция точки на сегмнет
    Dim pIntersection() As Point3d
    Dim MyLine          As LineElement
    
    Set MyLine = CreateLineElement2(Nothing, iPoint, iPoint)
    i = iLine.GetClosestSegment(iPoint)
    Set Segment = CreateLineElement2(Nothing, iLine.Vertex(i + 1), iLine.Vertex(i + 2))
    projectPoint = Segment.ProjectPointOnPerpendicular2(iPoint, Matrix3dIdentity)
    pIntersection() = Segment.AsIntersectableElement.GetIntersectionPoints(MyLine, Matrix3dIdentity)
    
        If UBound(pIntersection) = 0 Then
            DistancetoLine = 0
        Else: DistancetoLine = Point3dDistance(projectPoint, iPoint)
        End If
    
End Function

Private Sub PlacePoint(pPoint As Point3d)
    Dim MyLine As LineElement
    
    Set MyLine = CreateLineElement2(Nothing, pPoint, pPoint)
    MyLine.Level = ActiveDesignFile.Levels.Find(UserForm_Settings.ComboBox_level_point.Text)
    ActiveModelReference.AddElement MyLine
    MyLine.Redraw
End Sub

Attribute VB_Name = "UserForm_Settings"
Attribute VB_Base = "0{08C0F885-B5E0-45CB-A1E9-AD7372153AB9}{F3483764-5B85-40E9-89EA-F0505876EE3C}"
Attribute VB_GlobalNameSpace = False
Attribute VB_Creatable = False
Attribute VB_PredeclaredId = True
Attribute VB_Exposed = False
Attribute VB_TemplateDerived = False
Attribute VB_Customizable = False
Private Sub InizializeCell(myComboBox As ComboBox)
Dim MyCellEnum As CellInformationEnumerator
Dim MyCell As CellInformation
    myComboBox.Clear
    On Error GoTo EX
    Set MyCellEnum = Application.GetCellInformationEnumerator(False, False)
    While MyCellEnum.MoveNext
        Set MyCell = MyCellEnum.Current
        myComboBox.AddItem MyCell.Name
    Wend
EX:
inizialize_ListBox ListBox_levels
End Sub
Private Sub inizialize_ListBox(MyListBox As ListBox)
    Dim myLevel As Level
    Dim MyLevelName() As String
    ReDim MyLevelName(0)
    Dim MadeChange As Boolean
    Dim i As Integer
    Dim tmpName As String
    
        MyListBox.Clear
    For Each myLevel In ActiveDesignFile.Levels
        MyLevelName(UBound(MyLevelName)) = myLevel.Name
        ReDim Preserve MyLevelName(UBound(MyLevelName) + 1)
    Next
        ReDim Preserve MyLevelName(UBound(MyLevelName) - 1)
        
        MadeChange = True
        While MadeChange = True
            MadeChange = False
            For i = LBound(MyLevelName) To UBound(MyLevelName) - 1
                If StrComp(MyLevelName(i), MyLevelName(i + 1)) = 1 Then
                    tmpName = MyLevelName(i)
                    MyLevelName(i) = MyLevelName(i + 1)
                    MyLevelName(i + 1) = tmpName
                    MadeChange = True
                End If
            Next i
        Wend
        For i = LBound(MyLevelName) To UBound(MyLevelName)
            MyListBox.AddItem MyLevelName(i)
        Next i
End Sub


Private Sub CheckBox_useLevel_Change()
If CheckBox_useLevel.Value = True Then
    ListBox_levels.Enabled = True
ElseIf CheckBox_useLevel.Value = False Then
    ListBox_levels.Enabled = False
End If
End Sub



Private Sub cmbLevels_Change()
    UserForm_Cell_to_Point.CommandButton_cell_to_line.Enabled = True
End Sub

Private Sub ComboBox_edit_Change()
    UserForm_Cell_to_Point.CommandButton_Rail_Add.Enabled = True
    UserForm_Cell_to_Point.CommandButton_Rail_Move.Enabled = True
End Sub

Private Sub ComboBox_level_line_Change()
    UserForm_Cell_to_Point.CommandButton_draw_point.Enabled = True
End Sub

Private Sub ComboBox_Rail_Left_Change()
    UserForm_Cell_to_Point.CommandButton_Rail_L.Enabled = True
End Sub

Private Sub ComboBox_Rail_Left_DblClick(ByVal Cancel As MSForms.ReturnBoolean)
    InizializeCell UserForm_Settings.ComboBox_Rail_Left
End Sub

Private Sub ComboBox_Rail_Right_Change()
    UserForm_Cell_to_Point.CommandButton_Rail_R.Enabled = True
End Sub

Private Sub ComboBox_Rail_Right_DblClick(ByVal Cancel As MSForms.ReturnBoolean)
    InizializeCell UserForm_Settings.ComboBox_Rail_Right
End Sub

Private Sub UserForm_Initialize()
    InizializeCell UserForm_Settings.ComboBox_Rail_Left
    InizializeCell UserForm_Settings.ComboBox_Rail_Right
End Sub

Private Sub UserForm_QueryClose(Cancel As Integer, CloseMode As Integer)
    Cancel = 1
    UserForm_Settings.Hide
End Sub
