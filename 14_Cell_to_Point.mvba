Attribute VB_Name = "HookKey"
Option Explicit

Sub HookKey()
    Dim oMessage As CadInputMessage
    Set oMessage = CadInputQueue.GetInput
    Select Case oMessage.InputType
        Case msdCadInputTypeDataPoint
            CadInputQueue.SendDataPoint oMessage.Point
            CadInputQueue.SendKeyin "Travel step forward"
        Case msdCadInputTypeReset
            CadInputQueue.SendReset
    End Select
    
End Sub

Attribute VB_Name = "Inizialisation"
Sub InizialisationCells()
    Dim MyEnum As ElementEnumerator
    Dim myFilter As New ElementScanCriteria
    Dim MyCell As CellElement
    Dim i As Integer
    Dim bool As Boolean

    UserForm_Cell_to_Point.ComboBox_cell.Clear
    myFilter.ExcludeAllTypes
    myFilter.IncludeType msdElementTypeCellHeader
    
    Set MyEnum = ActiveModelReference.Scan(myFilter)
    
    While MyEnum.MoveNext
        Set MyCell = MyEnum.Current
            Do
                For i = 0 To UserForm_Cell_to_Point.ComboBox_cell.ListCount - 1
                    If UserForm_Cell_to_Point.ComboBox_cell.List(i, 0) = MyCell.Name Then
                        Exit Do
                    End If
                Next i
                UserForm_Cell_to_Point.ComboBox_cell.AddItem MyCell.Name
        Loop While bool = True
    Wend
           
End Sub

Attribute VB_Name = "LCE_Cell_to_Line"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private FirstCell As CellElement

Private Sub ILocateCommandEvents_Accept(ByVal Element As Element, Point As Point3d, ByVal View As View)
    Dim MyEnum As ElementEnumerator
    Dim myFilter As New ElementScanCriteria
    Dim MyEnum1 As ElementEnumerator
    Dim myFilter1 As New ElementScanCriteria
    Dim MyCell As CellElement
    Dim MinDist As Double 'Минимальное расстоияние между Cell
    Dim FirstPoint As Point3d ' Точка, которая определяется ближайшей к крайнему вертексу искомой линии - последующая для вхождения
    Dim MyLine() As Point3d
    Dim BoolDist As Boolean ' Условие проверки первой точки из выборки
    ReDim MyLine(0)
    Dim Line As LineElement ' Результирующая линия
    Dim tmpCell As CellElement 'Промежуточный фрагмент для поиска
    

    BoolDist = True
    
    
    FirstPoint = FirstCell.Origin
    ActiveModelReference.RemoveElement FirstCell
    MyLine(0) = FirstPoint
    ReDim Preserve MyLine(UBound(MyLine) + 1)
    myFilter.ExcludeAllTypes
    myFilter.IncludeType msdElementTypeCellHeader
    
    Set MyEnum = ActiveModelReference.Scan(myFilter)
    
    While MyEnum.MoveNext
        Set MyCell = MyEnum.Current
        If MyCell.Name = UserForm_Cell_to_Point.ComboBox_cell.Text Then
            myFilter1.ExcludeAllTypes
            myFilter1.IncludeType msdElementTypeCellHeader
            Set MyEnum1 = ActiveModelReference.Scan(myFilter1)
                While MyEnum1.MoveNext
                    If MyEnum1.Current.AsCellElement.Name = UserForm_Cell_to_Point.ComboBox_cell.Text Then
                        If BoolDist = True Then
                            MinDist = Point3dDistance(FirstPoint, MyEnum1.Current.AsCellElement.Origin)
                            Set tmpCell = MyEnum1.Current.AsCellElement
                            BoolDist = False
                        Else
                            If Point3dDistance(FirstPoint, MyEnum1.Current.AsCellElement.Origin) < MinDist Then ' Проверка всех фрагментов на минимальную дистанцию
                                MinDist = Point3dDistance(FirstPoint, MyEnum1.Current.AsCellElement.Origin)
                                Set tmpCell = MyEnum1.Current.AsCellElement
                            End If
                        End If
                    End If
                Wend
                FirstPoint = tmpCell.Origin
                ActiveModelReference.RemoveElement tmpCell
                MyLine(UBound(MyLine)) = FirstPoint
                ReDim Preserve MyLine(UBound(MyLine) + 1)
                BoolDist = True
        End If
    Wend
    ReDim Preserve MyLine(UBound(MyLine) - 1)
    Set Line = CreateLineElement1(Nothing, MyLine)
    ActiveModelReference.AddElement Line
    Line.Level = ActiveDesignFile.Levels.Find(ActiveSettings.Level.Name)
    Line.Redraw
    'Inizialisation.InizialisationCells
End Sub

Private Sub ILocateCommandEvents_Cleanup()

End Sub

Private Sub ILocateCommandEvents_Dynamics(Point As Point3d, ByVal View As View, ByVal DrawMode As MsdDrawingMode)

End Sub

Private Sub ILocateCommandEvents_LocateFailed()
    If UserForm_Cell_to_Point.ComboBox_cell.Text = "" Then
        MsgBox "Выберите Cell"
    End If
End Sub

Private Sub ILocateCommandEvents_LocateFilter(ByVal Element As Element, Point As Point3d, Accepted As Boolean)
Accepted = False


If Element.IsCellElement And Element.AsCellElement.Name = UserForm_Cell_to_Point.ComboBox_cell.Text Then
    Accepted = True
    Set FirstCell = Element.AsCellElement
End If
ShowCommand "Cells_to_Line"
ShowPrompt "Подтвердите выделение ЛКМ"
End Sub

Private Sub ILocateCommandEvents_LocateReset()

End Sub

Private Sub ILocateCommandEvents_Start()
    'CommandState.EnableAccuSnap
    ShowCommand "Cells_to_Line"
    ShowPrompt "Укажите начальный Cell"
End Sub

Attribute VB_Name = "Module1"
Sub Main()
    UserForm_Cell_to_Point.Show vbModeless
End Sub

Attribute VB_Name = "REplace"
Sub ReplaceCell()
    Dim MyEnum As ElementEnumerator
    Dim myFilter As New ElementScanCriteria
    Dim MyCell As CellElement
    Dim myPoint As LineElement
    Dim lvl As Level
    
    If UserForm_Cell_to_Point.ComboBox_cell.Text = "" Then
        MsgBox "Выберите Cell"
    End If

    myFilter.ExcludeAllTypes
    myFilter.IncludeType msdElementTypeCellHeader
    
    Set MyEnum = ActiveModelReference.Scan(myFilter)
    
    While MyEnum.MoveNext
        Set MyCell = MyEnum.Current
            If MyCell.Name = UserForm_Cell_to_Point.ComboBox_cell.Text Then
                Set myPoint = CreateLineElement2(MyCell, MyCell.Origin, MyCell.Origin)
                myPoint.Level = ActiveDesignFile.Levels.Find(ActiveSettings.Level.Name)
                ActiveModelReference.AddElement myPoint
                myPoint.Redraw
                    If UserForm_Cell_to_Point.CheckBox_delete_cell.Value = True Then
                        ActiveModelReference.RemoveElement MyCell
                        MyCell.Redraw
                    End If
            End If
    Wend
End Sub

Attribute VB_Name = "UserForm_Cell_to_Point"
Attribute VB_Base = "0{0BEAA765-26B5-40EC-B5D1-FA62CF98E2FA}{538A9820-83E4-4BB8-80CE-014BA09E1A7F}"
Attribute VB_GlobalNameSpace = False
Attribute VB_Creatable = False
Attribute VB_PredeclaredId = True
Attribute VB_Exposed = False
Attribute VB_TemplateDerived = False
Attribute VB_Customizable = False
Private Sub CommandButton_cell_to_line_Click()
    CommandState.StartLocate New LCE_Cell_to_Line
End Sub

Private Sub CommandButton_cie_Click()
    HookKey.HookKey
End Sub



Private Sub CommandButton_replace_Click()
    ReplaceCell
    Inizialisation.InizialisationCells
End Sub

Private Sub UserForm_Click()

End Sub

Private Sub UserForm_Initialize()
    InizialisationCells
End Sub
