Attribute VB_Name = "Connect"
Public Sub Connect(myLine As LineElement)
    Dim myEnum As ElementEnumerator
    Dim myFilter As New ElementScanCriteria
    Dim myAttach As Attachment
    Dim SharedCellEnum As ElementEnumerator
    Dim MinDist As Double
    Dim i As Long
    Dim tmpDist As LineElement
    Dim Dist3d As LineElement ' Результирующая минимальная дистанция
    Dim noSet As Boolean
    
    MinDist = CDbl(ufListLevels.TextBox_toleranceConnect.Text) * 0.01
    myFilter.ExcludeAllTypes
    myFilter.ExcludeAllLevels
    If (ufListLevels.cmbReference.Text) <> "" Then
            Set myAttach = ActiveModelReference.Attachments(ufListLevels.cmbReference.ListIndex + 1)
            
            
            myFilter.IncludeType msdElementTypeCellHeader
            myFilter.IncludeType msdElementTypeSharedCell
            myFilter.IncludeLevel ActiveModelReference.Attachments(ufListLevels.cmbReference.ListIndex + 1).Levels.Find("1001000")
            Set myEnum = myAttach.Scan(myFilter)
                While myEnum.MoveNext
                    Select Case myEnum.Current.Type
                        Case msdElementTypeSharedCell
                            Set SharedCellEnum = myEnum.Current.AsSharedCellElement.GetSubElements
                        Case msdElementTypeCellHeader
                            On Error Resume Next
                            Set SharedCellEnum = myEnum.Current.AsCellElement.GetSubElements
'errOpen:

                    End Select
                    While SharedCellEnum.MoveNext
                        Select Case SharedCellEnum.Current.Type
                            Case msdElementTypeLine
                                If SharedCellEnum.Current.AsLineElement.Length > 0 Then
                                    For i = 1 To (myLine.VerticesCount - 1)
                                        Set tmpDist = Dist3d_Segment_to_Segment(Segment3dFromPoint3dStartEnd(SharedCellEnum.Current.AsLineElement.StartPoint, SharedCellEnum.Current.AsLineElement.EndPoint), Segment3dFromPoint3dStartEnd(myLine.Vertex(i), myLine.Vertex(i + 1)))
                                        If tmpDist.Length < (MinDist) And tmpDist.Length > 0 Then
                                            Set Dist3d = tmpDist
                                            MinDist = tmpDist.Length
                                            notset = True
                                        End If
                                    Next i
                                End If
                        End Select
                    Wend
                Wend
        If notset = True Then
            ActiveModelReference.AddElement Dist3d
            Dist3d.Redraw
        Else: MsgBox "В радиусе поиска опора не найдена"
        End If
    ElseIf (ufListLevels.cmbReference.Text) = "" Then
        MsgBox "Укажите Reference с опопрами"
    End If
End Sub

Public Function Dist3d_Segment_to_Segment(segment1 As Segment3d, segment2 As Segment3d) As LineElement
    Dim StartPoint As Point3d
    Dim EndPoint As Point3d
    Dim Fraction0 As Double
    Dim Fraction1 As Double
    
    If Segment3dSegment3dClosestApproach(segment1, segment2, StartPoint, Fraction0, EndPoint, Fraction1) Then
        If Fraction0 > 1 Then
            StartPoint = segment1.EndPoint
        ElseIf Fraction0 < 0 Then
            StartPoint = segment1.StartPoint
        End If
        If Fraction1 > 1 Then
            EndPoint = segment2.EndPoint
        ElseIf Fraction1 < 0 Then
            EndPoint = segment2.StartPoint
        End If
        
        Set Dist3d_Segment_to_Segment = CreateLineElement2(Nothing, StartPoint, EndPoint)
        Debug.Print Fraction0 & "_" & Fraction1
    Else
        Set Dist3d_Segment_to_Segment = CreateLineElement2(Nothing, Point3dFromXYZ(0, 0, 0), Point3dFromXYZ(0, 0, 0))
    End If
    
'ActiveModelReference.AddElement Dist3d_Segment_to_Segment
'Dist3d_Segment_to_Segment.Color = 0
'Dist3d_Segment_to_Segment.Redraw
End Function

Attribute VB_Name = "GetAngle"
Option Explicit

Function GAngle(pSt As Point3d, pEnd As Point3d) As Double
Dim dAng As Double
Dim Angel As Double
Dim ang As Double
Dim dx As Double
Dim dy As Double
dx = pEnd.X - pSt.X
dy = pEnd.Y - pSt.Y
If dy <> 0 Then
    ang = Atn(dx / dy)
    If dx >= 0 And dy > 0 Then
        dAng = ang
    ElseIf dx >= 0 And dy < 0 Then
        dAng = ang + Pi
    ElseIf dx < 0 And dy < 0 Then
        dAng = ang + Pi
    ElseIf dx < 0 And dy > 0 Then
        dAng = ang + 2 * Pi
    End If
ElseIf dy = 0 Then

    If dx > 0 Then
        dAng = Pi / 2
    ElseIf dx < 0 Then
        dAng = 3 * Pi / 4
    End If
End If
Angel = Pi / 2 - dAng
GAngle = Angel
End Function

Attribute VB_Name = "Module1"
Public Consol As LineElement
Public Wire As LineElement
Public Sub DrawLine()
    CommandState.StartPrimitive New PCE_PlaceLineString, True
End Sub
Public Sub Conect()
    Dim myEnum As ElementEnumerator
    Dim bool As Boolean
    Set myEnum = ActiveModelReference.GetSelectedElements
    
    While myEnum.MoveNext
        If myEnum.Current.Type = msdElementTypeLine Or myEnum.Current.Type = msdElementTypeLineString Then
            Connect.Connect myEnum.Current.AsLineElement
            bool = True
        End If
    Wend
    If bool = False Then
        Connect.Connect ActiveModelReference.GraphicalElementCache.GetLastValidElement.AsLineElement
    End If
End Sub
Public Sub Join()
    Dim myEnum As ElementEnumerator
    Dim bool As Boolean
    Set myEnum = ActiveModelReference.GetSelectedElements
    
     While myEnum.MoveNext
        If myEnum.Current.Type = msdElementTypeLine Or myEnum.Current.Type = msdElementTypeLineString Then
            If UserForm.CheckBox_EndPoint.Value = True Then
             '   Set Consol = myEnum.Current.AsLineElement
                Module1.FindNerstVertex myEnum.Current.AsLineElement.Vertex(myEnum.Current.AsLineElement.VerticesCount)
            End If
            If UserForm.CheckBox_startPoint.Value = True Then
             '   Set Consol = myEnum.Current.AsLineElement
                Module1.FindNerstVertex myEnum.Current.AsLineElement.Vertex(1)
            End If
            
            bool = True
        End If
    Wend
    If bool = False Then
        Module1.FindNerstVertex ActiveModelReference.GraphicalElementCache.GetLastValidElement.AsLineElement.Vertex(ActiveModelReference.GraphicalElementCache.GetLastValidElement.AsLineElement.VerticesCount)
    End If
End Sub
Sub Main()
    UserForm.Show vbModeless
    inizializeNoLevel ufListLevels.lbNoLevels
End Sub
 
Public Sub FindNerstVertex(EndPoint As Point3d)
    Dim myEnum As ElementEnumerator
    Dim ComlexString As ElementEnumerator
    Dim myFilter As New ElementScanCriteria
    Dim i As Long
    Dim chkLevel As Boolean ' Выбран ли слой для привязки
    Dim minDistance As Double
    Dim tLineString As LineElement
    Dim j As Long
    Dim k As Integer
    Dim o As Long
    Dim movePoint As Point3d
    Dim tmpDist As Double
    
    minDistance = CDbl(ufListLevels.TextBox_tolerance.Text) * 0.01
    
    myFilter.ExcludeAllTypes
    myFilter.ExcludeAllLevels
    myFilter.IncludeType msdElementTypeLineString
    myFilter.IncludeType msdElementTypeComplexString
    
    chkLevel = False
        For k = 1 To ufListLevels.lbNoLevels.ListCount
            If ufListLevels.lbNoLevels.Selected(k - 1) Then
                myFilter.IncludeLevel ActiveDesignFile.Levels.Find(ufListLevels.lbNoLevels.List(k - 1))
                chkLevel = True
            End If
        Next k
        If chkLevel = False Then
            MsgBox "Выберите слой для привязки"
            Exit Sub
        End If
    Set myEnum = ActiveModelReference.Scan(myFilter)
        While myEnum.MoveNext
            Select Case myEnum.Current.Type
                Case msdElementTypeLineString
                    tmpDist = DistancetoLine(myEnum.Current.AsLineElement, EndPoint)
                    If tmpDist < minDistance Then
                        If tmpDist > 0 Then
                            minDistance = tmpDist
                            Set Wire = myEnum.Current.AsLineElement
                        End If
                    End If
                Case msdElementTypeComplexString
                    Set ComlexString = myEnum.Current.AsComplexStringElement.GetSubElements
                        While ComlexString.MoveNext
                            Select Case ComlexString.Current.Type
                                Case msdElementTypeLineString
                                    tmpDist = DistancetoLine(ComlexString.Current.AsLineElement, EndPoint)
                                    If tmpDist < minDistance Then
                                        If tmpDist > 0 Then
                                            minDistance = tmpDist
                                            Set Wire = ComlexString.Current.AsLineElement
                                        End If
                                    End If
                            End Select
                        Wend
            End Select
        Wend
            If UserForm.OptionButton_add_vertex.Value = True Then
                InsertVertex Wire, EndPoint
            Else
                j = Wire.GetClosestVertex(EndPoint)
                Wire.ModifyVertex j, EndPoint
                Wire.Rewrite
                Wire.Redraw
            End If
End Sub

 Function DistancetoLine(iLine As LineElement, iPoint As Point3d) As Double
    Dim i As Long ' Индекс билжайшего вертекса
    Dim MinI As Long
    Dim dist As Double
    Dim tmpDist As Double
    Dim Seg() As Point3d
    Seg = GetClosestSegment3d(iLine, iPoint)
'    For i = j To j + 1
  '     dist = Dist_Segment_to_Point(iLine.Vertex(i), iLine.Vertex(i + 1), iPoint)
 '           If i = 1 Then
 '               tmpDist = dist
  '          End If
 '           If dist < tmpDist Then
  '          tmpDist = dist
  '      End If
  '  Next i
    DistancetoLine = Dist_Segment_to_Point(Seg(0), Seg(1), iPoint)
End Function

Private Function Dist_Segment_to_Point(StartPoint As Point3d, EndPoint As Point3d, iPoint As Point3d) As Double
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    
    vPoint = Vector3dSubtractPoint3dPoint3d(iPoint, StartPoint)
    vLine = Vector3dSubtractPoint3dPoint3d(EndPoint, StartPoint)
    
    c1 = Vector3dDotProduct(vPoint, vLine)
    c2 = Vector3dDotProduct(vLine, vLine)
        If c1 <= 0 Then
            Dist_Segment_to_Point = Point3dDistance(StartPoint, iPoint)
        ElseIf c2 <= c1 Then
            Dist_Segment_to_Point = Point3dDistance(EndPoint, iPoint)
        Else
            k = c1 / c2
            vProject = Vector3dScale(vLine, k)
            pProject = Vector3dAdd(Vector3dFromPoint3d(StartPoint), vProject)
            Dist_Segment_to_Point = Point3dDistance(Point3dFromVector3d(pProject), iPoint)
        End If
End Function
Function GetClosestSegment3d(iLine As LineElement, iPoint As Point3d) As Point3d()
    Dim i As Long
    Dim Segment(0 To 1) As Point3d ' 0 - start , 1 - end
    i = iLine.GetClosestVertex(iPoint)
        If i = 0 Then
            Segment(0) = iLine.Vertex(1)
            Segment(1) = iLine.Vertex(2)
        ElseIf i = (iLine.VerticesCount - 1) Then
            Segment(0) = iLine.Vertex((iLine.VerticesCount) - 1)
            Segment(1) = iLine.Vertex(iLine.VerticesCount)
        Else
            i = i + 1
            If Dist_Segment_to_Point(iLine.Vertex(i), iLine.Vertex(i + 1), iPoint) >= Dist_Segment_to_Point(iLine.Vertex(i - 1), iLine.Vertex(i), iPoint) Then
                Segment(0) = iLine.Vertex(i - 1)
                Segment(1) = iLine.Vertex(i)
            Else
                Segment(0) = iLine.Vertex(i)
                Segment(1) = iLine.Vertex(i + 1)
            End If
        End If
    GetClosestSegment3d = Segment
End Function


' Function DistancetoLine(iLine As LineElement, iPoint As Point3d) As Double
'
'    Dim segment As LineElement
'    Dim segment1 As LineElement
'
'    Dim i As Integer ' Индекс билжайшего вертекса
'    Dim projectPoint As Point3d ' Проекция точки на сегмнет
'    Dim projectPoint1 As Point3d
'    Dim tmpDist As Double
'    Dim dist As Double
'
'    For i = 1 To iLine.VerticesCount - 1 'Step 2
'        Set segment = CreateLineElement2(Nothing, iLine.Vertex(i), iLine.Vertex(i + 1))
' '       projectPoint = segment.ProjectPointOnPerpendicular2(iPoint, Matrix3dIdentity)
'        dist = Dist_segment_to_line(segment, iPoint)
'            If i = 1 Then
'                tmpDist = dist
'            End If
'        If dist < tmpDist Then
'            tmpDist = dist
'        End If
'    Next i
'DistancetoLine = tmpDist
'End Function



'Private Function Dist_segment_to_line(iLine As LineElement, iPoint As Point3d) As Double
'    Dim vPoint As Vector3d
'    Dim vLine As Vector3d
'    Dim vProject As Vector3d
'    Dim i As Long ' Индекс билжайшего вертекса
'    Dim segment As LineElement
'    Dim ax As Double
'    Dim ay As Double
'    Dim az As Double
'    Dim c1 As Double 'Скалярное произведение vPoint x vLine
'    Dim c2 As Double 'Скалярное произведение vline x vLine
'    Dim k As Double ' Коэффециент проекции
'    Dim pProject As Point3d
'
''    i = iLine.GetClosestSegment(iPoint)
' '   Set segment = iLine
'
'    ax = iPoint.X - iLine.StartPoint.X
'    ay = iPoint.Y - iLine.StartPoint.Y
'    az = iPoint.Z - iLine.StartPoint.Z
'
'    vPoint = Vector3dFromXYZ(ax, ay, az)
'
'    ax = iLine.EndPoint.X - iLine.StartPoint.X
'    ay = iLine.EndPoint.Y - iLine.StartPoint.Y
'    az = iLine.EndPoint.Z - iLine.StartPoint.Z
'
'    vLine = Vector3dFromXYZ(ax, ay, az)
'
'    c1 = Vector3dDotProduct(vPoint, vLine)
'    c2 = Vector3dDotProduct(vLine, vLine)
'
'        If c1 <= 0 Then
'            Dist_segment_to_line = Point3dDistance(iLine.StartPoint, iPoint)
'        ElseIf c2 <= c1 Then
'            Dist_segment_to_line = Point3dDistance(iLine.EndPoint, iPoint)
'        ElseIf c1 = iLine.Length * Point3dDistance(iPoint, iLine.StartPoint) Then
'            Dist_segment_to_line = Point3dDistance(iPoint, iPoint)
'        Else
'            k = c1 / c2
'            vProject = Vector3dScale(vLine, k)
'            pProject.X = iLine.StartPoint.X + vProject.X
'            pProject.Y = iLine.StartPoint.Y + vProject.Y
'            pProject.Z = iLine.StartPoint.Z + vProject.Z
'            Dist_segment_to_line = Point3dDistance(pProject, iPoint)
'        End If
'End Function



Public Sub InsertVertex(iLine As LineElement, iPoint As Point3d)
    Dim i As Long
    i = iLine.GetClosestSegment(iPoint)
    iLine.InsertVertex i + 1, iPoint
    iLine.Rewrite
    iLine.Redraw
    
End Sub

Public Sub inizializeNoLevel(MyListBox As ListBox)
    Dim myLevel As Level
    Dim MyLevelName() As String
    ReDim MyLevelName(0)
    Dim MadeChange As Boolean
    Dim i As Integer
    Dim tmpName As String
        MyListBox.Clear
    For Each myLevel In ActiveDesignFile.Levels
        MyLevelName(UBound(MyLevelName)) = myLevel.Name
        ReDim Preserve MyLevelName(UBound(MyLevelName) + 1)
    Next
        ReDim Preserve MyLevelName(UBound(MyLevelName) - 1)
        
        MadeChange = True
        While MadeChange = True
            MadeChange = False
            For i = LBound(MyLevelName) To UBound(MyLevelName) - 1
                If StrComp(MyLevelName(i), MyLevelName(i + 1)) = 1 Then
                    tmpName = MyLevelName(i)
                    MyLevelName(i) = MyLevelName(i + 1)
                    MyLevelName(i + 1) = tmpName
                    MadeChange = True
                End If
            Next i
        Wend
        For i = LBound(MyLevelName) To UBound(MyLevelName)
            MyListBox.AddItem MyLevelName(i)
        Next i
End Sub

Attribute VB_Name = "PCE_Line"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IPrimitiveCommandEvents
Dim bool As Boolean
Dim bPoint As Point3d

Private Sub IPrimitiveCommandEvents_Cleanup()

End Sub

Private Sub IPrimitiveCommandEvents_DataPoint(Point As Point3d, ByVal View As View)
Dim myLine As LineElement
    If bool = False Then
        bPoint = Point
        CommandState.StartDynamics
        bool = True
    ElseIf bool = True Then
        Set Consol = CreateLineElement2(Nothing, bPoint, Point)
      '  Module1.CheckLevel MyLine
        ActiveModelReference.AddElement Consol
        Consol.Redraw
        bool = False
        CommandState.StopDynamics
                FindNerstVertex Point
            Connect.Connect Consol
    End If
        
End Sub

Private Sub IPrimitiveCommandEvents_Dynamics(Point As Point3d, ByVal View As View, ByVal DrawMode As MsdDrawingMode)
    Dim myLine As LineElement
    Set myLine = CreateLineElement2(Nothing, bPoint, Point)
    myLine.Redraw DrawMode
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
End Sub
'Private Sub FindNerstVertex(nLevel As String, endPoint As Point3d)
'    Dim myEnum As ElementEnumerator
'    Dim myFilter As New ElementScanCriteria
'    Dim i As Long
'    Dim minDistance As Double
'    Dim tLineString As LineElement
'    Dim j As Long
'    Dim movePoint As Point3d
'    minDistance = 50000000
'
'    myFilter.ExcludeAllTypes
'    myFilter.ExcludeAllLevels
'    myFilter.IncludeLevel ActiveDesignFile.Levels(nLevel)
'    myFilter.IncludeType msdElementTypeLineString
'    myFilter.IncludeType msdElementTypeComplexString
'
'    Set myEnum = ActiveModelReference.Scan(myFilter)
'        While myEnum.MoveNext
'            Select Case myEnum.Current.Type
'                Case msdElementTypeLineString
'                    If DistancetoLine(myEnum.Current.AsLineElement, endPoint) < minDistance Then
'                        minDistance = DistancetoLine(myEnum.Current.AsLineElement, endPoint)
'                        Set tLineString = myEnum.Current.AsLineElement
'                    End If
'            End Select
'        Wend
'  ' If UserForm.CheckBox_join.Value = False Then
'        j = tLineString.GetClosestVertex(endPoint)
'        tLineString.ModifyVertex j, endPoint
'        tLineString.Rewrite
'        tLineString.Redraw
' '   End If
'
'End Sub
'
' Private Function DistancetoLine(iLine As LineElement, iPoint As Point3d) As Double
'
'    Dim segment As LineElement
'    Dim i As Long ' Индекс билжайшего вертекса
'    Dim projectPoint As Point3d ' Проекция точки на сегмнет
'
'    i = iLine.GetClosestSegment(iPoint)
'    Set segment = CreateLineElement2(Nothing, iLine.Vertex(i + 1), iLine.Vertex(i + 2))
'    segment.Color = 0
'    ActiveModelReference.AddElement segment
'    segment.Redraw
'    projectPoint = segment.ProjectPointOnPerpendicular2(iPoint, Matrix3dIdentity)
'    DistancetoLine = Point3dDistance(projectPoint, iPoint)
'
'End Function
'

Attribute VB_Name = "PCE_LineString_Rotation"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IPrimitiveCommandEvents

Private Sub IPrimitiveCommandEvents_Cleanup()

End Sub

Private Sub IPrimitiveCommandEvents_DataPoint(Point As Point3d, ByVal View As View)

End Sub

Private Sub IPrimitiveCommandEvents_Dynamics(Point As Point3d, ByVal View As View, ByVal DrawMode As MsdDrawingMode)
    Dim RotationMatrix As Matrix3d
    RotationMatrix = Matrix3dFromAxisAndRotationAngle(2, GetAngle.GAngle(Consol.Vertex(1), Point))
    Consol.Rotate
End Sub

Private Sub IPrimitiveCommandEvents_Keyin(ByVal Keyin As String)

End Sub

Private Sub IPrimitiveCommandEvents_Reset()

End Sub

Private Sub IPrimitiveCommandEvents_Start()
    CommandState.EnableAccuSnap
    CommandState.StartDynamics
End Sub

Attribute VB_Name = "PCE_PlaceLineString"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IPrimitiveCommandEvents
Private LineVert() As Point3d
Dim boolset As Boolean

Private Sub IPrimitiveCommandEvents_Cleanup()

End Sub

Private Sub IPrimitiveCommandEvents_DataPoint(Point As Point3d, ByVal View As View)
    If boolset = False Then
        LineVert(UBound(LineVert)) = Point
        CommandState.StartDynamics
        boolset = True
    ElseIf boolset = True Then
        LineVert(UBound(LineVert)) = Point
'            If UBound(LineVert) > 2 And Point3dDistance(Point, LineVert(0)) = 0 Then ' Проверка на замыкание, если текущая точка совпадает с первой, то создается Shape
'                Set myShape = CreateShapeElement1(Nothing, LineVert)
'                ActiveModelReference.AddElement myShape
'                myShape.Redraw
'            End If
    End If
ReDim Preserve LineVert(UBound(LineVert) + 1)
'Placements.MoveView Point, View
End Sub

Private Sub IPrimitiveCommandEvents_Dynamics(Point As Point3d, ByVal View As View, ByVal DrawMode As MsdDrawingMode)
    Dim LineString As LineElement
    LineVert(UBound(LineVert)) = Point
    Set LineString = CreateLineElement1(Nothing, LineVert)
    LineString.Redraw DrawMode
End Sub

Private Sub IPrimitiveCommandEvents_Keyin(ByVal Keyin As String)
     Select Case UCase(Keyin)
        Case "SAS"
            ReDim Preserve LineVert(UBound(LineVert) - 1)
    End Select
End Sub

Private Sub IPrimitiveCommandEvents_Reset()
 '   Dim LineString As LineElement
    ReDim Preserve LineVert(UBound(LineVert) - 1)
    Set Consol = CreateLineElement1(Nothing, LineVert)
    ActiveModelReference.AddElement Consol
    Consol.Redraw
    CommandState.StartDefaultCommand
           ' If UserForm.CheckBox_join.Value = False Then
        If UserForm.CheckBox_EndPoint.Value = True And UserForm.CheckBox_startPoint.Value = True Then
            FindNerstVertex Consol.Vertex(1)
            FindNerstVertex Consol.Vertex(Consol.VerticesCount)
        ElseIf UserForm.CheckBox_EndPoint.Value = True Then
            FindNerstVertex Consol.Vertex(Consol.VerticesCount)
        ElseIf UserForm.CheckBox_startPoint.Value = True Then
            FindNerstVertex Consol.Vertex(1)
        End If
        
           ' End If
           'Connect.Connect Consol
End Sub

Private Sub IPrimitiveCommandEvents_Start()
    ReDim LineVert(0)
    CommandState.EnableAccuSnap
End Sub

Attribute VB_Name = "UserForm"
Attribute VB_Base = "0{6D89DA50-EDE0-4A3A-8FE9-B25CC4C5F873}{8BEC0AFC-5A17-43C6-9A81-C2A1481B7439}"
Attribute VB_GlobalNameSpace = False
Attribute VB_Creatable = False
Attribute VB_PredeclaredId = True
Attribute VB_Exposed = False
Attribute VB_TemplateDerived = False
Attribute VB_Customizable = False

Private Sub CheckBox_join_Change()
    If CheckBox_join.Value = True Then
        CommandButton_join.Enabled = True
    Else
        CommandButton_join.Enabled = False
    End If
End Sub

Private Sub button_SelectLevel_Click()
    ufListLevels.Show vbModeless
End Sub

Private Sub CommandButton_draw_line_Click()
    CommandState.StartPrimitive New PCE_Line, True
End Sub

'Private Sub CheckBox_startPoint_Change()
'    If CheckBox_startPoint.Value = True Then
'        If CheckBox_EndPoint.Value = True Then
'            OptionButton_add_vertex.Value = True
'        End If
'  '  Else if CheckBox_startPoint.Value = false then
'    End If
'End Sub
Private Sub CommandButton_conection_Click()
    Module1.Conect
    'Connect.Connect ActiveModelReference.GraphicalElementCache.GetLastValidElement.AsLineElement
End Sub

Private Sub CommandButton_draw_line_string_Click()
    CommandState.StartPrimitive New PCE_PlaceLineString, True
End Sub

Private Sub CommandButton_join_Click()
   ' If UserForm.OptionButton_add_vertex.Value = True Then
    '   ' InsertVertex Wire, CommandState.LastDataPoint
   ' Else
       ' Module1.FindNerstVertex ActiveModelReference.GraphicalElementCache.GetLastValidElement.AsLineElement.Vertex(ActiveModelReference.GraphicalElementCache.GetLastValidElement.AsLineElement.VerticesCount)
   ' End If
   Module1.Join
End Sub

Attribute VB_Name = "ufListLevels"
Attribute VB_Base = "0{644AAB12-FDDC-45AD-9858-7C879F767578}{F5911A6C-3C2A-47FA-A3A7-D9E9FD985E58}"
Attribute VB_GlobalNameSpace = False
Attribute VB_Creatable = False
Attribute VB_PredeclaredId = True
Attribute VB_Exposed = False
Attribute VB_TemplateDerived = False
Attribute VB_Customizable = False

Option Explicit
Private Sub button_closeNoLevel_Click()
    ufListLevels.Hide
End Sub


Private Sub cmbReference_DblClick(ByVal Cancel As MSForms.ReturnBoolean)
    inizializeRef
End Sub

Private Sub UserForm_Initialize()
    inizializeRef
End Sub

Private Sub UserForm_QueryClose(Cancel As Integer, CloseMode As Integer)
   Cancel = 1
   ufListLevels.Hide
End Sub

Private Sub inizializeRef()

Dim myLevel As Level
Dim MyModel As ModelReference
Dim myAttachment As Attachment
Set MyModel = ActiveModelReference
    cmbReference.Clear
    For Each myAttachment In MyModel.Attachments
       ' Debug.Print myAttachment.AttachName
        cmbReference.AddItem myAttachment.AttachName
       ' Debug.Print "ListIndex = " & cmbReference.ListIndex
       ' Debug.Print myAttachment.Name
        myAttachment.LogicalName = myAttachment.AttachName
    Next
End Sub

'Private Sub cmbReference_Change()
'    Dim myAttach As Attachment
'    Dim myModelRef As ModelReference
'    Dim myLevel As Level
'    Set myAttach = ActiveModelReference.Attachments(cmbReference.ListIndex + 1)
'        Debug.Print myAttach.AttachName
''        cmbLevels.Clear
''            For Each myLevel In myAttach.Levels
''                cmbLevels.AddItem myLevel.Name
''            Next
'End Sub
