Attribute VB_Name = "LCE_CutRoad"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Implements ILocateCommandEvents
Dim CutShape As ClosedElement
Private SelElement As Element ' Элемент, по которому будет обрезаться дорога
Private Sub ILocateCommandEvents_Accept(ByVal Element As Element, Point As Point3d, ByVal View As View)
    Dim oElement() As Element
    Dim MyEnum As ElementEnumerator
    Dim Rshape As ComplexShapeElement 'Результирующий shape
    Dim cut As Boolean
    ReDim oElement(0)
    Set oElement(0) = Element
    Set MyEnum = CutShape.GetDifferenceShapesFromRegion(oElement, Nothing, msdFillModeFilled)
    While MyEnum.MoveNext
        Select Case MyEnum.Current.Type
            Case msdElementTypeComplexShape
                If cut = False Then ActiveModelReference.RemoveElement CutShape
                Set Rshape = MyEnum.Current
                Rshape.FillMode = msdFillModeNotFilled
                ActiveModelReference.AddElement Rshape
                Rshape.Redraw
                cut = True
        End Select
    Wend
    Set CutShape = Rshape
End Sub

Private Sub ILocateCommandEvents_Cleanup()

End Sub

Private Sub ILocateCommandEvents_Dynamics(Point As Point3d, ByVal View As View, ByVal DrawMode As MsdDrawingMode)

End Sub

Private Sub ILocateCommandEvents_LocateFailed()

End Sub

Private Sub ILocateCommandEvents_LocateFilter(ByVal Element As Element, Point As Point3d, Accepted As Boolean)
    Accepted = False
    If Element.IsShapeElement Or Element.IsComplexShapeElement Then
        Set SelElement = Element
        Accepted = True
        ActiveModelReference.SelectElement Element, True
        ShowCommand "Стыковка дорог"
        ShowPrompt "Подтвердите выделение нажав левой кнопкой мыши"
    End If
End Sub

Private Sub ILocateCommandEvents_LocateReset()
    CommandState.StartDefaultCommand
End Sub

Private Sub ILocateCommandEvents_Start()
    Set CutShape = MyShape
End Sub

Attribute VB_Name = "Module1"
Option Explicit
Public MyShape As ShapeElement ' Контур дороги до стыковки

Sub Main()
MyForm.show vbModeless
End Sub
'Sub offsetPlus()
'    MyForm.tbOffset.Text = (CDbl(MyForm.tbOffset.Text) + CDbl(MyForm.tbStep.Text))
'End Sub
'Sub offsetMinus()
'    MyForm.tbOffset.Text = (CDbl(MyForm.tbOffset.Text) - CDbl(MyForm.tbStep.Text))
'End Sub

Attribute VB_Name = "MyForm"
Attribute VB_Base = "0{D0F7D896-D85B-4C74-AFC8-A3AF5FF72575}{0C4EFE7F-ED92-44AE-9561-B765F784980B}"
Attribute VB_GlobalNameSpace = False
Attribute VB_Creatable = False
Attribute VB_PredeclaredId = True
Attribute VB_Exposed = False
Attribute VB_TemplateDerived = False
Attribute VB_Customizable = False
Option Explicit



Private Sub cmbDraw_Click()
    CommandState.StartPrimitive New PCE_DynamicRoad, True
End Sub

Attribute VB_Name = "PCE_DynamicRoad"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents
Dim boolset As Boolean
Dim CentreLine() As Point3d
Dim V As Long ' Количество вертексов осевой линии
Dim LLine() As Point3d
Dim RLine() As Point3d
Dim Offset() As Double ' Значения офсетов для каждого вертекса
    'Dim P0 As Point3d
    'Dim P1 As Point3d
    'Dim P2 As Point3d
    'Dim P3 As Point3d
Private Sub IPrimitiveCommandEvents_Cleanup()

End Sub
Private Sub IPrimitiveCommandEvents_DataPoint(Point As Point3d, ByVal View As View)
    Dim Offs As Double
    ' Если включены и правая и левая, то ширина берется между ними,
    ' если только левая или правая, между центральной и крайней
    Offs = CDbl(MyForm.tbOffset.Text)
    If MyForm.cbRight.Value = True And MyForm.cbLeft.Value = True Then
            Offs = CDbl(MyForm.tbOffset.Text) * 0.5
    End If
    
    If boolset = False Then
            V = 0
            CentreLine(V) = Point
            Offset(V) = Offs
            V = V + 1
            ReDim Preserve CentreLine(V)
            ReDim Preserve LLine(V)
            ReDim Preserve RLine(V)
            ReDim Preserve Offset(V)
            CommandState.StartDynamics
            boolset = True
        Else
            CentreLine(V) = Point
            Offset(V) = Offs
            V = V + 1
            ReDim Preserve CentreLine(V)
            ReDim Preserve LLine(V)
            ReDim Preserve RLine(V)
            ReDim Preserve Offset(V)
    End If
    
    If MyForm.CheckBox_MoveView.Value Then
        MoveView Point, View
    End If
End Sub
Private Sub IPrimitiveCommandEvents_Dynamics(Point As Point3d, ByVal View As View, ByVal DrawMode As MsdDrawingMode)
    Dim LLs As LineElement
    Dim RLs As LineElement
    Dim Cline As LineElement
    Dim dist As TextElement
    
    
    Dim IPl As Point3d
    Dim IPr As Point3d
    Dim p(0 To 3) As Point3d
    Dim Offs As Double
    ' Если включены и правая и левая, то ширина берется между ними,
    ' если только левая или правая, между центральной и крайней
    Offs = CDbl(MyForm.tbOffset.Text)
    If MyForm.cbRight.Value = True And MyForm.cbLeft.Value = True Then
            Offs = CDbl(MyForm.tbOffset.Text) * 0.5
    End If
    CentreLine(V) = Point
    p(0) = Perpendicular(CentreLine(V - 1), CentreLine(V), Offset(V - 1))(0)
    p(1) = Perpendicular(CentreLine(V - 1), CentreLine(V), Offset(V - 1))(1)
    p(2) = Perpendicular(CentreLine(V - 1), CentreLine(V), Offs)(2)
    p(3) = Perpendicular(CentreLine(V - 1), CentreLine(V), Offs)(3)
    LLine(V) = p(2)
    RLine(V) = p(3)
        If V = 1 Then
                p(0) = Perpendicular(CentreLine(V - 1), CentreLine(V), Offs)(0)
                p(1) = Perpendicular(CentreLine(V - 1), CentreLine(V), Offs)(1)
                LLine(V - 1) = p(0)
                RLine(V - 1) = p(1)
            ElseIf V > 1 Then
                IPl = IntersectionLines(LLine(V - 2), LLine(V - 1), p(0), p(2))
                IPr = IntersectionLines(RLine(V - 2), RLine(V - 1), p(1), p(3))
                LLine(V - 1) = IPl
                RLine(V - 1) = IPr
        End If
    If MyForm.cbLeft.Value = True Then
        Set LLs = CreateLineElement1(Nothing, LLine)
        LLs.Color = CDbl(MyForm.tbColorL.Text)
        LLs.Redraw DrawMode
    End If
    
    If MyForm.cbRight.Value = True Then
        Set RLs = CreateLineElement1(Nothing, RLine)
        RLs.Color = CDbl(MyForm.tbColorR.Text)
        RLs.Redraw DrawMode
    End If
    
    If MyForm.cbCentral.Value = True Then
        Set Cline = CreateLineElement1(Nothing, CentreLine)
        Cline.Color = CDbl(MyForm.tbColorC.Text)
        Cline.Redraw DrawMode
        Set dist = CreateTextElement1(Nothing, Round(Point3dDistanceXY(CentreLine(V - 1), CentreLine(V)), 2), Point, Matrix3dIdentity)
        dist.Redraw DrawMode
    End If
    
    If MyForm.CheckBox_MoveView.Value Then
        Dim mBord As ShapeElement
        Dim pB(0 To 3) As Point3d
        Dim sc As Double
        sc = CDbl(MyForm.TextBox_AreaHit.Text) * 0.005
        
        pB(0) = Point3dFromXY(View.Center.X - View.Extents.X * sc, View.Center.Y - View.Extents.Y * sc)
        pB(1) = Point3dFromXY(View.Center.X + View.Extents.X * sc, View.Center.Y - View.Extents.Y * sc)
        pB(2) = Point3dFromXY(View.Center.X + View.Extents.X * sc, View.Center.Y + View.Extents.Y * sc)
        pB(3) = Point3dFromXY(View.Center.X - View.Extents.X * sc, View.Center.Y + View.Extents.Y * sc)
        
        Set mBord = CreateShapeElement1(Nothing, pB)
        mBord.LineWeight = 0
        mBord.LineStyle = ActiveDesignFile.LineStyles("3")
        mBord.Color = 80
        mBord.Transparency = 0.8
        
        mBord.Redraw DrawMode
    End If
End Sub


Sub MoveView(mPoint As Point3d, mView As View)
    Dim width As Double
    Dim height As Double
    Dim PCentr As Point3d
    
    PCentr = ActiveDesignFile.Views(mView.Index).Center
    width = ActiveDesignFile.Views(mView.Index).Extents.X
    height = ActiveDesignFile.Views(mView.Index).Extents.Y
            If Abs(mPoint.X - PCentr.X) >= (width * CDbl(MyForm.TextBox_AreaHit.Text) * 0.005) Or Abs(mPoint.Y - PCentr.Y) >= (height * CDbl(MyForm.TextBox_AreaHit.Text) * 0.005) Then
                ActiveDesignFile.Views(mView.Index).Center = mPoint
                ActiveDesignFile.Views(mView.Index).Redraw
            Else
                ActiveDesignFile.Views(mView.Index).Redraw
            End If
End Sub

Private Sub IPrimitiveCommandEvents_Keyin(ByVal Keyin As String)

End Sub
Private Sub IPrimitiveCommandEvents_Reset()
    Dim line As LineElement
    Dim LL As LineElement
    Dim RL As LineElement
    
    'Dim Shape As ShapeElement
    Dim i As Double
    Dim j As Double
    Dim k As Double
    k = V
    j = 0
    Dim sh() As Point3d
    ReDim sh(0)
    For i = 0 To ((2 * V) + 1)
        ReDim Preserve sh(i)
            If j <= V Then
                If MyForm.cbLeft.Value = True And MyForm.cbCentral.Value = True Then
                    sh(i) = LLine(j)
                    j = j + 1
                ElseIf MyForm.cbLeft.Value = False Then
                    sh(i) = CentreLine(j)
                    j = j + 1
                End If
                
            Else
                If MyForm.cbRight.Value = True Then
                    sh(i) = RLine(k)
                    k = k - 1
                ElseIf MyForm.cbRight.Value = False Then
                    sh(i) = CentreLine(k)
                    k = k - 1
                End If
        End If
        
    Next i
    If MyForm.cbCreateShape.Value = True Then
        Set MyShape = CreateShapeElement1(Nothing, sh)
        ActiveModelReference.AddElement MyShape
        MyShape.FillMode = msdFillModeNotFilled
        MyShape.Redraw
    ElseIf MyForm.cbCreateShape.Value = False Then
        If MyForm.cbLeft.Value = True Then
            Set LL = CreateLineElement1(Nothing, LLine)
            LL.Color = CDbl(MyForm.tbColorL.Text)
            ActiveModelReference.AddElement LL
            LL.Redraw
        End If
    
        If MyForm.cbRight.Value = True Then
            Set RL = CreateLineElement1(Nothing, RLine)
            RL.Color = CDbl(MyForm.tbColorR.Text)
            ActiveModelReference.AddElement RL
            RL.Redraw
        End If
    
        If MyForm.cbCentral.Value = True Then
            Set line = CreateLineElement1(Nothing, CentreLine)
            line.Color = CDbl(MyForm.tbColorC.Text)
            ActiveModelReference.AddElement line
            line.Redraw
            line.Rewrite
        End If
    End If
    CommandState.StartDefaultCommand
    CommandState.StartLocate New LCE_CutRoad
    ShowCommand "Стыковка дорог"
    ShowPrompt "Выделите дорогу к которой пристыковаться"
End Sub
Private Sub IPrimitiveCommandEvents_Start()
    ReDim CentreLine(0)
    ReDim LLine(0)
    ReDim RLine(0)
    ReDim Offset(0)
    CommandState.EnableAccuSnap
End Sub

'-----функция поиска точки пересечения прямых, заданных соответствующими парами координат-----

Function IntersectionLines(PP1 As Point3d, PP2 As Point3d, PP3 As Point3d, PP4 As Point3d) As Point3d
    Dim k1 As Double
    Dim k2 As Double
    Dim b1 As Double
    Dim b2 As Double
    If PP1.X = PP2.X And PP3.X = PP4.X And PP2.X = PP3.X Then
            IntersectionLines.X = PP2.X
            IntersectionLines.Y = PP2.Y
        ElseIf PP3.X = PP4.X Then
            k1 = (PP2.Y - PP1.Y) / (PP2.X - PP1.X)
            b1 = (PP1.Y * PP2.X - PP2.Y * PP1.X) / (PP2.X - PP1.X)
            IntersectionLines.X = PP3.X
            IntersectionLines.Y = k1 * PP3.X + b1
        ElseIf PP1.X = PP2.X Then
            k2 = (PP4.Y - PP3.Y) / (PP4.X - PP3.X)
            b2 = (PP3.Y * PP4.X - PP4.Y * PP3.X) / (PP4.X - PP3.X)
            IntersectionLines.X = PP1.X
            IntersectionLines.Y = k2 * PP1.X + b2
        Else
            k1 = (PP2.Y - PP1.Y) / (PP2.X - PP1.X)
            b1 = (PP1.Y * PP2.X - PP2.Y * PP1.X) / (PP2.X - PP1.X)
            k2 = (PP4.Y - PP3.Y) / (PP4.X - PP3.X)
            b2 = (PP3.Y * PP4.X - PP4.Y * PP3.X) / (PP4.X - PP3.X)
            IntersectionLines.X = (b2 - b1) / (k1 - k2)
            IntersectionLines.Y = (k1 * (b2 - b1) / (k1 - k2)) + b1
    End If
End Function

Function Perpendicular(PP1 As Point3d, PP2 As Point3d, Of As Double) As Point3d()
    Dim PP(0 To 3) As Point3d ' Искомые точки перпендикуляров
                                ' 0 - 1 - перпендикуляры на начале отрезка Лево - Право, соответственно
                                ' 2 - 3 - перпендикуляры на конце отрезка Лево - Право, соответственно
    
    Dim vRoad As Vector3d   ' Точка сдвига относительно осевой линии
    
    vRoad = Vector3dUnitPerpendicularXY(Vector3dSubtractPoint3dPoint3d(PP2, PP1))
    vRoad = Vector3dScale(vRoad, Of)
    PP(0) = Point3dAddPoint3dVector3d(PP1, vRoad)
    PP(2) = Point3dAddPoint3dVector3d(PP2, vRoad)
    vRoad = Vector3dScale(vRoad, -1)
    PP(1) = Point3dAddPoint3dVector3d(PP1, vRoad)
    PP(3) = Point3dAddPoint3dVector3d(PP2, vRoad)
    Perpendicular = PP
End Function
