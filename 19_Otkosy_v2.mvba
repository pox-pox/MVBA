Attribute VB_Name = "LCE_brovka_podoshva"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private Brovka As LineElement
Private Podoshva As LineElement
Private pBrovka() As Point3d
Private pPodoshva() As Point3d
Private pik As Double
Private i As Long
Private j As Double
Private k As Long
Private bool As Double



Private Sub ILocateCommandEvents_Accept(ByVal Element As Element, Point As Point3d, ByVal View As View)
MsgBox Brovka.VerticesCount & " " & " " & Podoshva.VerticesCount
'ReDim pBrovka(0)
'ReDim pPodoshva(0)
Dim Shtrih As LineElement
Dim NoClipShtrih As LineElement
Dim pShtrih As Point3d
Dim pIntirsection() As Point3d

Dim m As Long
Dim SegmentVector As Vector3d
Dim vShtrix As Vector3d
Dim vPoint As Vector3d
Dim pPoint() As Point3d
Dim mPoint As EllipseElement ' Точка укрепленного откоса
ReDim pPoint(0)

Dim dir As Integer ' Направление штрихов
Dim l As Long ' Коэффециент длины штриха

pik = CDbl(UserForm1.TextBox_offset_shtrih.Text)
dir = -1

i = Fix(Brovka.Length / pik)

For k = 0 To i
    ReDim Preserve pBrovka(k)
    pBrovka(k) = Brovka.PointAtDistance(k * pik)
Next k

For k = 0 To UBound(pBrovka())
    l = 10000
    m = Brovka.GetClosestSegment(pBrovka(k))
    SegmentVector = Vector3dFromXY(Brovka.Vertex(m + 2).X - Brovka.Vertex(m + 1).X, Brovka.Vertex(m + 2).Y - Brovka.Vertex(m + 1).Y)
    vShtrix = Vector3dUnitPerpendicularXY(SegmentVector)
        If (k Mod 2) = 0 Then
            If UserForm1.CheckBox_short_shtrih.Value = True Then
                l = CDbl(UserForm1.TextBox_short_shtlih_L.Text)
            End If
        End If
    vShtrix = Vector3dScale(vShtrix, dir * l)
    pShtrih.X = pBrovka(k).X + Vector3dGetComponent(vShtrix, 0)
    pShtrih.Y = pBrovka(k).Y + Vector3dGetComponent(vShtrix, 1)
    Set NoClipShtrih = CreateLineElement2(Nothing, pBrovka(k), pShtrih)
'    ActiveModelReference.AddElement NoClipShtrih
'    NoClipShtrih.Redraw
    pIntirsection = Podoshva.AsIntersectableElement.GetIntersectionPointsOnIntersector(NoClipShtrih, Matrix3dIdentity)
        ReDim Preserve pPodoshva(k)
            If (k Mod 2) = 0 And UserForm1.CheckBox_short_shtrih.Value = True Then
                    pPodoshva(k) = pShtrih
                    If UserForm1.CheckBox_ukrOtkos.Value = True Then
                        vPoint = Vector3dScale(vShtrix, 1 + CDbl(UserForm1.TextBox_uOtkos_d.Text) / l) 'Вектор точки
                        pPoint(UBound(pPoint)) = Point3dAddPoint3dVector3d(pBrovka(k), vPoint)
                        ReDim Preserve pPoint(UBound(pPoint) + 1)
                    End If
            Else
                If UBound(pIntirsection) = 0 Then
                    pPodoshva(k) = pIntirsection(0)
                Else
                    pPodoshva(k) = pBrovka(k)
                End If
            End If
Next k

'j = Podoshva.Length / i
'For k = 0 To i
'    ReDim Preserve pPodoshva(k)
'    pPodoshva(k) = Podoshva.PointAtDistance(k * j)
'Next k
For k = 0 To UBound(pBrovka())
    Set strih = CreateLineElement2(Nothing, pBrovka(k), pPodoshva(k))
    If strih.Length <> 0 Then
        ActiveModelReference.AddElement strih
        strih.Redraw
    End If
    
Next k
If UserForm1.CheckBox_ukrOtkos.Value = True Then
    ReDim Preserve pPoint(UBound(pPoint) - 1)
    For k = 0 To UBound(pPoint)
        Set mPoint = CreateEllipseElement2(Nothing, pPoint(k), CDbl(UserForm1.TextBox_uOtkos_r.Text), CDbl(UserForm1.TextBox_uOtkos_r.Text), Matrix3dIdentity)
        ActiveModelReference.AddElement mPoint
        mPoint.Redraw
    Next k
End If

End Sub

Private Sub ILocateCommandEvents_Cleanup()

End Sub

Private Sub ILocateCommandEvents_Dynamics(Point As Point3d, ByVal View As View, ByVal DrawMode As MsdDrawingMode)

End Sub

Private Sub ILocateCommandEvents_LocateFailed()

End Sub

Private Sub ILocateCommandEvents_LocateFilter(ByVal Element As Element, Point As Point3d, Accepted As Boolean)
Accepted = False

If Element.Type = msdElementTypeLineString Then
    If bool = False Then
        Set Brovka = Element.AsLineElement
        bool = True
    ElseIf bool = True Then
        Set Podoshva = Element.AsLineElement
        Accepted = True
    End If
End If

End Sub

Private Sub ILocateCommandEvents_LocateReset()

End Sub

Private Sub ILocateCommandEvents_Start()
    CommandState.EnableAccuSnap
End Sub
Private Sub GE()

End Sub

Attribute VB_Name = "Module1"
Sub Main()
   UserForm1.Show vbModeless
End Sub

Attribute VB_Name = "UserForm1"
Attribute VB_Base = "0{F6528452-0DF8-4160-89F2-66D42A0A1F17}{1556C071-CA50-41AD-8FBB-0DE7C8698F4F}"
Attribute VB_GlobalNameSpace = False
Attribute VB_Creatable = False
Attribute VB_PredeclaredId = True
Attribute VB_Exposed = False
Attribute VB_TemplateDerived = False
Attribute VB_Customizable = False
Private Sub CommandButton1_Click()
    CommandState.StartLocate New LCE_brovka_podoshva
End Sub
