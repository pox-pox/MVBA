Attribute VB_Name = "Module1"
Sub main()
    UserForm1.Show vbModeless
End Sub

Attribute VB_Name = "PCE_Border"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents


Private Sub IPrimitiveCommandEvents_Cleanup()

End Sub

Private Sub IPrimitiveCommandEvents_DataPoint(point As Point3d, ByVal View As View)
'    Dim oMessage As CadInputMessage
'    On Error GoTo exitCIQ
'        Do While True
'            Set oMessage = CadInputQueue.GetInput
'            Select Case oMessage.InputType
'                Case msdCadInputTypeDataPoint
                    CadInputQueue.SendDataPoint point
                    MoveView point, oMessage.View
                    ActiveDesignFile.Views(oMessage.View.Index).Redraw
'                Case msdCadInputTypeKeyin
'                    CadInputQueue.SendKeyin oMessage.Keyin
'                Case msdCadInputTypeReset
'                    CadInputQueue.SendReset
'                    CommandButton_MoveView.Visible = True
'                    Exit Do
'            End Select
'        Loop
'exitCIQ:

End Sub

Private Sub IPrimitiveCommandEvents_Dynamics(point As Point3d, ByVal View As View, ByVal DrawMode As MsdDrawingMode)
    Dim mBord As ShapeElement
    Dim pB(0 To 3) As Point3d
    Dim sc As Double
    sc = CDbl(UserForm1.TextBox1.Text) * 0.005
    
    pB(0) = Point3dFromXY(View.Center.X - View.Extents.X * sc, View.Center.Y - View.Extents.Y * sc)
    pB(1) = Point3dFromXY(View.Center.X + View.Extents.X * sc, View.Center.Y - View.Extents.Y * sc)
    pB(2) = Point3dFromXY(View.Center.X + View.Extents.X * sc, View.Center.Y + View.Extents.Y * sc)
    pB(3) = Point3dFromXY(View.Center.X - View.Extents.X * sc, View.Center.Y + View.Extents.Y * sc)
    
    Set mBord = CreateShapeElement1(Nothing, pB)
    mBord.LineWeight = 2
    mBord.LineStyle = ActiveDesignFile.LineStyles("3")
    mBord.Color = 5
    mBord.Transparency = 0.8
    
    mBord.Redraw DrawMode
    
End Sub

Private Sub IPrimitiveCommandEvents_Keyin(ByVal Keyin As String)

End Sub

Private Sub IPrimitiveCommandEvents_Reset()
    CommandState.StartDefaultCommand
End Sub

Private Sub IPrimitiveCommandEvents_Start()
    CommandState.StartDynamics
End Sub

Sub MoveView(mPoint As Point3d, mView As View)
    Dim width As Double
    Dim height As Double
    Dim PCentr As Point3d
    
    PCentr = ActiveDesignFile.Views(mView.Index).Center
    width = ActiveDesignFile.Views(mView.Index).Extents.X
    height = ActiveDesignFile.Views(mView.Index).Extents.Y
            If Abs(mPoint.X - PCentr.X) >= (width * 0.25) Or Abs(mPoint.Y - PCentr.Y) >= (height * 0.25) Then
                ActiveDesignFile.Views(mView.Index).Center = mPoint
                ActiveDesignFile.Views(mView.Index).Redraw
            Else
                ActiveDesignFile.Views(mView.Index).Redraw
            End If
       
    
End Sub

Attribute VB_Name = "UserForm1"
Attribute VB_Base = "0{D02324D9-0094-4CD1-B586-CC5DF6B020E7}{4ACC0EF3-EA9D-4BBB-8912-70CAF0A7D48A}"
Attribute VB_GlobalNameSpace = False
Attribute VB_Creatable = False
Attribute VB_PredeclaredId = True
Attribute VB_Exposed = False
Attribute VB_TemplateDerived = False
Attribute VB_Customizable = False
Sub HookKey()
    Dim oMessage As CadInputMessage
    Dim mPoint As LineElement
    Dim point As Point3d
    
    On Error GoTo exitCIQ
        Do While True
            Set oMessage = CadInputQueue.GetInput
            Select Case oMessage.InputType
                Case msdCadInputTypeDataPoint
                   
                    CadInputQueue.SendDataPoint oMessage.point
                    point = oMessage.point
                    MoveView oMessage.point, oMessage.View
                    'CommandState.StartPrimitive New PCE_Border, True
'                    ActiveDesignFile.Views(oMessage.View.Index).Redraw
'                    Set mPoint = CreateLineElement2(Nothing, point, point)
'                    mPoint.LineWeight = 5
'                    mPoint.Color = 2
                   ' ActiveModelReference.AddElement mPoint
'                    mPoint.Redraw msdDrawingModeTemporaryErase
'                    mPoint.Rewrite
                Case msdCadInputTypeKeyin
                    CadInputQueue.SendKeyin oMessage.Keyin
                Case msdCadInputTypeReset
                    CadInputQueue.SendReset
                    CommandButton_MoveView.Visible = True
                    Exit Do
            End Select
        Loop
exitCIQ:
End Sub
Sub MoveView(mPoint As Point3d, mView As View)
    Dim width As Double
    Dim height As Double
    Dim PCentr As Point3d
    
    PCentr = ActiveDesignFile.Views(mView.Index).Center
    width = ActiveDesignFile.Views(mView.Index).Extents.X
    height = ActiveDesignFile.Views(mView.Index).Extents.Y
            If Abs(mPoint.X - PCentr.X) >= (width * 0.25) Or Abs(mPoint.Y - PCentr.Y) >= (height * 0.25) Then
                ActiveDesignFile.Views(mView.Index).Center = mPoint
                ActiveDesignFile.Views(mView.Index).Redraw
            Else
                ActiveDesignFile.Views(mView.Index).Redraw
            End If
End Sub

Private Sub CommandButton_MoveView_Click()
   CommandButton_MoveView.Visible = False
  ' CommandState.StartPrimitive New PCE_Border, True
   HookKey
End Sub
