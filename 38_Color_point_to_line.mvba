Attribute VB_Name = "Draw_point"


Public Sub DrawPoint()
    Dim myEnum As ElementEnumerator
    Dim InsideEnum As ElementEnumerator
    Dim ComplexString As ElementEnumerator
    Dim myFilter As New ElementScanCriteria
    Dim aLine() As Element
    Dim lComplex() As Element
    Dim l As Long
    Dim pIntersection() As Point3d
    Dim i As Long
    Dim k As Long
    Dim j As Long
    Dim count As Long
    Dim pStart As Point3d
    Dim pEnd As Point3d
    Dim pSwitch As LineElement
    Dim currentLine As Element
    Dim complex As ElementEnumerator
    Dim first As Boolean
    myFilter.ExcludeAllTypes
    myFilter.ExcludeAllLevels
    
    myFilter.IncludeLevel ActiveDesignFile.Levels(UserForm_Settings.ComboBox_level_line.Text)
    myFilter.IncludeType msdElementTypeLineString
    myFilter.IncludeType msdElementTypeComplexString
    
    Set myEnum = ActiveModelReference.Scan(myFilter)
    aLine() = myEnum.BuildArrayFromContents
    
    For i = 0 To UBound(aLine)
        Select Case aLine(i).Type
            Case msdElementTypeLineString
                pStart = aLine(i).AsLineElement.StartPoint
                pEnd = aLine(i).AsLineElement.EndPoint
            Case msdElementTypeComplexString
                pStart = aLine(i).AsComplexStringElement.StartPoint
                pEnd = aLine(i).AsComplexStringElement.EndPoint
        End Select
        For k = 0 To UBound(aLine)
            If k <> i Then
                Select Case aLine(k).Type
                    Case msdElementTypeLineString
                        If DistancetoLine(aLine(k).AsLineElement, pEnd) = 0 Then
                            PlacePoint pEnd
                            count = count + 1
                        End If
                        If DistancetoLine(aLine(k).AsLineElement, pStart) = 0 Then
                            PlacePoint pStart
                            count = count + 1
                        End If
                    Case msdElementTypeComplexString
                       ' lComplex = aLine(k).AsComplexStringElement.GetSubElements.BuildArrayFromContents
                        Set complex = aLine(k).AsComplexStringElement.GetSubElements
                        lComplex() = complex.BuildArrayFromContents
                       ' While complex.MoveNext
                        For l = 0 To UBound(lComplex)
                         
                            Select Case lComplex(l).Type
                                Case msdElementTypeLineString
                                
                                    If DistancetoLine(lComplex(l).AsLineElement, pStart) = 0 Then
                                        If l = 0 Then
                                            PlacePoint pStart
                                            count = count + 1
                                        End If
                                        If l > 0 Then
                                            If DistancetoLine(lComplex(l).AsLineElement, pStart) <> DistancetoLine(lComplex(l - 1).AsLineElement, pStart) Then
                                                PlacePoint pStart
                                                count = count + 1
                                            End If
                                        End If
                                        
                                            
                                    End If
                                    If DistancetoLine(lComplex(l).AsLineElement, pEnd) = 0 Then
                                        If l = 0 Then
                                            PlacePoint pEnd
                                            count = count + 1
                                        End If
                                        If l > 0 Then
                                            If DistancetoLine(lComplex(l).AsLineElement, pEnd) <> DistancetoLine(lComplex(l - 1).AsLineElement, pEnd) Then
                                                PlacePoint pEnd
                                                count = count + 1
                                            End If
                                        End If
                                        
                                    End If
                                    
                            End Select
                        Next l
                        'Wend
                End Select
            End If
        Next k
    Next i
        
        
        
'
'        Set currentLine = aLine(i)
'        For k = 0 To UBound(aLine)
'            If k <> i Then
'                pIntersection() = currentLine.AsIntersectableElement.GetIntersectionPointsOnIntersector(aLine(k), Matrix3dIdentity)
'                If UBound(pIntersection) >= 0 Then
'                    For j = 0 To UBound(pIntersection)
'                        Select Case aLine(i).Type
'                            Case msdElementTypeLineString
'                                pStart = aLine(i).AsLineElement.StartPoint
'                                pEnd = aLine(i).AsLineElement.EndPoint
'                                        If UBound(pIntersection) > 0 And j < UBound(pIntersection) Then
'                                            If Point3dEqualTolerance(pIntersection(j), pIntersection(j + 1), 0) = True Then
'                                                k = k + 1
'                                                j = j + 1
'                                            End If
'                                        End If
'                            Case msdElementTypeComplexString
'                                pStart = aLine(i).AsComplexStringElement.StartPoint
'                                pEnd = aLine(i).AsComplexStringElement.EndPoint
'                                Set complex = aLine(i).AsComplexStringElement.GetSubElements
'                                While complex.MoveNext
'                                    Select Case complex.Current.Type
'                                        Case msdElementTypeLineString
'                                            If first = False Then
'                                                pStart = complex.Current.AsLineElement.StartPoint
'                                                pEnd = complex.Current.AsLineElement.EndPoint
'                                                first = True
'                                            ElseIf first = True Then
'                                                pEnd = complex.Current.AsLineElement.EndPoint
'                                            End If
'                                    End Select
'                                Wend
'
'                        End Select
'                                If Point3dEqualTolerance(pIntersection(j), pStart, 0) = True Or Point3dEqualTolerance(pIntersection(j), pEnd, 0) = True Then
'                                    Set pSwitch = CreateLineElement2(Nothing, pIntersection(j), pIntersection(j))
'                                    pSwitch.Level = ActiveDesignFile.Levels.Find(UserForm_Cell_to_Point.ComboBox_level_point.Text)
'                                    ActiveModelReference.AddElement pSwitch
'                                    pSwitch.Redraw
'                                    count = count + 1
'
'                                End If
'                    Next j
'                End If
'            End If
'        Next k
'    Next i
'
    
    
'
'    While MyEnum.MoveNext
'        Select Case MyEnum.Current.Type
'            Case msdElementTypeLineString
'
'            Case msdElementTypeComplexString
'    Wend
MsgBox "Создано точек: " & count
End Sub

Function DistancetoLine(iLine As LineElement, iPoint As Point3d) As Double

    Dim Segment As LineElement
    Dim i As Long ' Индекс билжайшего вертекса
    Dim projectPoint As Point3d ' Проекция точки на сегмнет
    Dim pIntersection() As Point3d
    Dim MyLine As LineElement
    
    Set MyLine = CreateLineElement2(Nothing, iPoint, iPoint)
    i = iLine.GetClosestSegment(iPoint)
    Set Segment = CreateLineElement2(Nothing, iLine.Vertex(i + 1), iLine.Vertex(i + 2))
  '  segment.Color = 0
  '  ActiveModelReference.AddElement segment
  '  segment.Redraw
    projectPoint = Segment.ProjectPointOnPerpendicular2(iPoint, Matrix3dIdentity)
    pIntersection() = Segment.AsIntersectableElement.GetIntersectionPoints(MyLine, Matrix3dIdentity)
    
    If UBound(pIntersection) = 0 Then
        DistancetoLine = 0
    Else: DistancetoLine = Point3dDistance(projectPoint, iPoint)
    End If
    
End Function

Private Sub PlacePoint(pPoint As Point3d)
    Dim MyLine As LineElement
    
    Set MyLine = CreateLineElement2(Nothing, pPoint, pPoint)
    MyLine.Level = ActiveDesignFile.Levels.Find(UserForm_Settings.ComboBox_level_point.Text)
    ActiveModelReference.AddElement MyLine
    MyLine.Redraw
End Sub

Attribute VB_Name = "HookKey"
Option Explicit

Sub HookKey()
    Dim oMessage As CadInputMessage
    Dim rotation As Matrix3d
    Dim transform As Transform3d
    Dim MyCell As CellElement
    Do While True
        Set oMessage = CadInputQueue.GetInput
        Select Case oMessage.InputType
            Case msdCadInputTypeDataPoint
                CadInputQueue.SendDataPoint oMessage.Point
                
               ' myCell.Redraw
                CadInputQueue.SendKeyin "Travel step forward"
                ActiveDesignFile.Views(oMessage.View.Index).Redraw
                rotation = Matrix3dInverse(oMessage.View.rotation)
                Set MyCell = ActiveModelReference.GraphicalElementCache.GetLastValidElement.AsCellElement
                transform = Transform3dFromMatrix3dAndFixedPoint3d(rotation, MyCell.Origin)
                MyCell.transform transform
                MyCell.Rewrite
            Case msdCadInputTypeKeyin
                CadInputQueue.SendKeyin oMessage.Keyin
            Case msdCadInputTypeReset
                CadInputQueue.SendReset
                Exit Do
        End Select
    Loop
End Sub

Attribute VB_Name = "Inizialisation"
Sub InizialisationCells()
    Dim myEnum As ElementEnumerator
    Dim myFilter As New ElementScanCriteria
    Dim MyCell As CellElement
    Dim i As Integer
    Dim bool As Boolean

    UserForm_Cell_to_Point.ComboBox_cell.Clear
    myFilter.ExcludeAllTypes
    myFilter.IncludeType msdElementTypeCellHeader
    
    Set myEnum = ActiveModelReference.Scan(myFilter)
    
    While myEnum.MoveNext
 '   On Error GoTo errOpen
            Set MyCell = myEnum.Current
                Do
                    For i = 0 To UserForm_Cell_to_Point.ComboBox_cell.ListCount - 1
                        If UserForm_Cell_to_Point.ComboBox_cell.List(i, 0) = MyCell.Name Then
                            Exit Do
                        End If
                    Next i
                    UserForm_Cell_to_Point.ComboBox_cell.AddItem MyCell.Name
            Loop While bool = True

    Wend
'errOpen:
           
End Sub

Attribute VB_Name = "LCE_Cell_to_Line"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private FirstCell As LineElement


Private Sub ILocateCommandEvents_Accept(ByVal Element As Element, Point As Point3d, ByVal View As View)
    Dim myEnum As ElementEnumerator
    Dim myFilter As New ElementScanCriteria
    Dim MyEnum1 As ElementEnumerator
    Dim myFilter1 As New ElementScanCriteria
    Dim MyCell As LineElement
    Dim minDist As Double 'Минимальное расстоияние между Cell
    Dim FirstPoint As Point3d ' Точка, которая определяется ближайшей к крайнему вертексу искомой линии - последующая для вхождения
    Dim MyLine() As Point3d
    Dim BoolDist As Boolean ' Условие проверки первой точки из выборки
    ReDim MyLine(0)
    Dim Line As LineElement ' Результирующая линия
    Dim tmpCell As LineElement 'Промежуточный фрагмент для поиска
    

    BoolDist = True
    
    
    FirstPoint = FirstCell.StartPoint
    
    ActiveModelReference.RemoveElement FirstCell
    MyLine(0) = FirstPoint
    ReDim Preserve MyLine(UBound(MyLine) + 1)
    myFilter.ExcludeAllTypes
    myFilter.IncludeType msdElementTypeLine
    
    
    Set myEnum = ActiveModelReference.Scan(myFilter)
    
    While myEnum.MoveNext
        Set MyCell = myEnum.Current
       ' If MyCell.Name = CellName Then
            myFilter1.ExcludeAllTypes
            
            myFilter1.IncludeType msdElementTypeLine
            Set MyEnum1 = ActiveModelReference.Scan(myFilter1)
                While MyEnum1.MoveNext
                    If MyEnum1.Current.AsLineElement.Color = CellName Then
                        If BoolDist = True Then
                            minDist = Point3dDistance(FirstPoint, MyEnum1.Current.AsLineElement.StartPoint)
                            Set tmpCell = MyEnum1.Current.AsLineElement
                            BoolDist = False
                        Else
                            If Point3dDistance(FirstPoint, MyEnum1.Current.AsLineElement.StartPoint) < minDist Then ' Проверка всех фрагментов на минимальную дистанцию
                                minDist = Point3dDistance(FirstPoint, MyEnum1.Current.AsLineElement.StartPoint)
                                Set tmpCell = MyEnum1.Current.AsLineElement
                            End If
                        End If
                    End If
                Wend
                FirstPoint = tmpCell.AsLineElement.StartPoint
                ActiveModelReference.RemoveElement tmpCell
                MyLine(UBound(MyLine)) = FirstPoint
                ReDim Preserve MyLine(UBound(MyLine) + 1)
                BoolDist = True
       ' End If
    Wend
    ReDim Preserve MyLine(UBound(MyLine) - 1)
    Set Line = CreateLineElement1(Nothing, MyLine)
    Line.Level = ActiveDesignFile.Levels.Find(UserForm_Settings.cmbLevels.Text)
    ActiveModelReference.AddElement Line
   ' Line.Level = ActiveDesignFile.Levels.Find(ActiveSettings.Level.Name)
    Line.Redraw
   ' UserForm_Cell_to_Point.Label6.Caption = ""
    'Inizialisation.InizialisationCells
End Sub

Private Sub ILocateCommandEvents_Cleanup()

End Sub

Private Sub ILocateCommandEvents_Dynamics(Point As Point3d, ByVal View As View, ByVal DrawMode As MsdDrawingMode)

End Sub

Private Sub ILocateCommandEvents_LocateFailed()
'    If UserForm_Cell_to_Point.ComboBox_cell.Text = "" Then
'        MsgBox "Выберите Cell"
'    End If
End Sub

Private Sub ILocateCommandEvents_LocateFilter(ByVal Element As Element, Point As Point3d, Accepted As Boolean)
Accepted = False
Debug.Print Element.Type

If Element.IsLineElement Then 'And Element.AsCellElement.Name = UserForm_Cell_to_Point.ComboBox_cell.Text
    Accepted = True
    Set FirstCell = Element.AsLineElement
    CellName = Element.Color
   ' UserForm_Cell_to_Point.Label6.Caption = Element.AsCellElement.Name
End If
ShowCommand "Cells_to_Line"
ShowPrompt "Подтвердите выделение ЛКМ"
End Sub

Private Sub ILocateCommandEvents_LocateReset()

End Sub

Private Sub ILocateCommandEvents_Start()
    'CommandState.EnableAccuSnap
    ShowCommand "Cells_to_Line"
    ShowPrompt "Укажите начальный Cell"
End Sub

Attribute VB_Name = "LCE_Line_Snap"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private mElement As Element
Private Join As Boolean
Private okPoint As Point3d



Private Sub ILocateCommandEvents_Accept(ByVal Element As Element, Point As Point3d, ByVal View As View)
    Dim mPoint As LineElement
    Dim prPoint As Point3d
    Dim k As Long
    
    Dim myEnum As ElementEnumerator
    Dim myFilter As New ElementScanCriteria
    Dim myComplexString() As Element
    
    myFilter.ExcludeAllTypes
    myFilter.IncludeType msdElementTypeLineString
    myFilter.IncludeType msdElementTypeComplexString
    myFilter.IncludeOnlyVisible
    
    If UserForm_Settings.CheckBox_useLevel.Value = True Then
        myFilter.ExcludeAllLevels
        For k = 1 To UserForm_Settings.ListBox_levels.ListCount
            If UserForm_Settings.ListBox_levels.Selected(k - 1) Then
                myFilter.IncludeLevel ActiveDesignFile.Levels.Find(UserForm_Settings.ListBox_levels.List(k - 1))
            End If
        Next k
    End If
    
    prPoint = Project_Point1(Element, Point)
    okPoint = prPoint
    Join = False
    Set myEnum = ActiveModelReference.Scan(myFilter)
        While myEnum.MoveNext
            Select Case myEnum.Current.Type
                Case msdElementTypeLineString
                    If Point3dDistanceXY(prPoint, myEnum.Current.AsLineElement.StartPoint) <= CDbl(UserForm_Settings.TextBox_searhRadius.Text) Then
                        myEnum.Current.AsLineElement.ModifyVertex 0, prPoint
                        myEnum.Current.AsLineElement.Rewrite
                        myEnum.Current.AsLineElement.Redraw
                        Join = True
                    ElseIf Point3dDistanceXY(prPoint, myEnum.Current.AsLineElement.EndPoint) <= CDbl(UserForm_Settings.TextBox_searhRadius.Text) Then
                        myEnum.Current.AsLineElement.ModifyVertex (myEnum.Current.AsLineElement.VerticesCount - 1), prPoint
                        myEnum.Current.AsLineElement.Rewrite
                        myEnum.Current.AsLineElement.Redraw
                        Join = True
                    End If
                Case msdElementTypeComplexString
                    myComplexString = myEnum.Current.AsComplexStringElement.GetSubElements.BuildArrayFromContents
                        Select Case myComplexString(0).Type
                            Case msdElementTypeLineString
                                If Point3dDistanceXY(myComplexString(0).AsLineElement.StartPoint, prPoint) <= CDbl(UserForm_Settings.TextBox_searhRadius.Text) Then
                                    myComplexString(0).AsLineElement.ModifyVertex 0, prPoint
                                    myComplexString(0).AsLineElement.Rewrite
                                    myComplexString(0).AsLineElement.Redraw
                                    Join = True
                                End If
                            Case msdElementTypeLine
                                If Point3dDistanceXY(myComplexString(0).AsLineElement.StartPoint, prPoint) <= CDbl(UserForm_Settings.TextBox_searhRadius.Text) Then
                                    myComplexString(0).AsLineElement.ModifyVertex 0, prPoint
                                    myComplexString(0).AsLineElement.Rewrite
                                    myComplexString(0).AsLineElement.Redraw
                                    Join = True
                                End If
                        End Select
                        
                        Select Case myComplexString(UBound(myComplexString)).Type
                            Case msdElementTypeLineString
                                If Point3dDistanceXY(myComplexString(UBound(myComplexString)).AsLineElement.EndPoint, prPoint) <= CDbl(UserForm_Settings.TextBox_searhRadius.Text) Then
                                    myComplexString(UBound(myComplexString)).AsLineElement.ModifyVertex (myComplexString(UBound(myComplexString)).AsLineElement.VerticesCount - 1), prPoint
                                    myComplexString(UBound(myComplexString)).AsLineElement.Rewrite
                                    myComplexString(UBound(myComplexString)).AsLineElement.Redraw
                                    Join = True
                                End If
                            Case msdElementTypeLine
                                If Point3dDistanceXY(myComplexString(UBound(myComplexString)).AsLineElement.EndPoint, prPoint) <= CDbl(UserForm_Settings.TextBox_searhRadius.Text) Then
                                    myComplexString(UBound(myComplexString)).AsLineElement.ModifyVertex (myComplexString(UBound(myComplexString)).AsLineElement.VerticesCount - 1), prPoint
                                    myComplexString(UBound(myComplexString)).AsLineElement.Rewrite
                                    myComplexString(UBound(myComplexString)).AsLineElement.Redraw
                                    Join = True
                                End If
                        End Select
            End Select
        Wend
    
'    Set mPoint = CreateLineElement2(Nothing, prPoint, prPoint)
'    ActiveModelReference.AddElement mPoint
'    mPoint.Redraw
If Join = False Then
    CommandState.StopDynamics
End If
End Sub

Private Sub ILocateCommandEvents_Cleanup()

End Sub

Private Sub ILocateCommandEvents_Dynamics(Point As Point3d, ByVal View As View, ByVal DrawMode As MsdDrawingMode)
    Dim prPoint As Point3d
    Dim perpend As LineElement
    Dim jOk As TextElement
    
    
    If Join = False Then
        prPoint = Project_Point1(mElement, Point)
        Set perpend = CreateLineElement2(Nothing, Point, prPoint)
        perpend.LineWeight = 0
        perpend.Color = 4
        perpend.Redraw DrawMode
    ElseIf Join = True Then
        Set jOk = CreateTextElement1(Nothing, "OK", okPoint, Matrix3dIdentity)
        jOk.TextStyle.Height = 0.1
        jOk.TextStyle.Width = 0.1
        jOk.Redraw DrawMode
    End If
    
End Sub

Private Sub ILocateCommandEvents_LocateFailed()

End Sub

Private Sub ILocateCommandEvents_LocateFilter(ByVal Element As Element, Point As Point3d, Accepted As Boolean)
Dim k As Long
Accepted = False
    If Element.IsLineElement Or Element.IsComplexElement Then
        If UserForm_Settings.CheckBox_useLevel.Value = False Then
            Accepted = True
            Set mElement = Element
            CommandState.StartDynamics
            Join = False
        ElseIf UserForm_Settings.CheckBox_useLevel.Value = True Then
            For k = 1 To UserForm_Settings.ListBox_levels.ListCount
                If UserForm_Settings.ListBox_levels.Selected(k - 1) Then
                    If Element.Level.Name = UserForm_Settings.ListBox_levels.List(k - 1) Then
                        Accepted = True
                        Set mElement = Element
                        CommandState.StartDynamics
                        Join = False
                    End If
                End If
            Next k
        End If
    End If
End Sub

Private Sub ILocateCommandEvents_LocateReset()
    CommandState.StopDynamics
    CommandState.StartDefaultCommand
End Sub

Private Sub ILocateCommandEvents_Start()
    ShowCommand "Snap"
    ShowPrompt "Укажите ось"

End Sub

Private Function Project_Point1(mLine As Element, mPoint As Point3d) As Point3d
   
Dim mComplexStr As ElementEnumerator
Dim i As Long
Dim j As Long
Dim minDist As Double
Dim tmpDist As Double
Dim tmpP As Point3d

    Select Case mLine.Type
        Case msdElementTypeLineString
            minDist = 500000
                tmpP = mPoint
                i = mLine.AsLineElement.GetClosestSegment(tmpP)
                tmpP.Z = mLine.AsLineElement.Vertex(i + 1).Z * 0.5 + mLine.AsLineElement.Vertex(i + 2).Z * 0.5

                tmpDist = Dist_Segment_to_Point(mLine.AsLineElement.Vertex(i + 1), mLine.AsLineElement.Vertex(i + 2), tmpP)
                    If tmpDist < minDist Then
                        minDist = tmpDist
                        Project_Point1 = Project_Point(mLine.AsLineElement.Vertex(i + 1), mLine.AsLineElement.Vertex(i + 2), tmpP)
                    End If
        Case msdElementTypeComplexString
            Set mComplexStr = mLine.AsComplexStringElement.GetSubElements
                minDist = 5000000
                While mComplexStr.MoveNext
                    Select Case mComplexStr.Current.Type
                        Case msdElementTypeLineString
                            tmpP = mPoint
                            i = mComplexStr.Current.AsLineElement.GetClosestSegment(tmpP)
                            tmpP.Z = mComplexStr.Current.AsLineElement.Vertex(i + 1).Z * 0.5 + mComplexStr.Current.AsLineElement.Vertex(i + 2).Z * 0.5
                            tmpDist = Dist_Segment_to_Point(mComplexStr.Current.AsLineElement.Vertex(i + 1), mComplexStr.Current.AsLineElement.Vertex(i + 2), tmpP)
                                If tmpDist < minDist Then
                                    minDist = tmpDist
                                    Project_Point1 = Project_Point(mComplexStr.Current.AsLineElement.Vertex(i + 1), mComplexStr.Current.AsLineElement.Vertex(i + 2), tmpP)
                                End If
                        Case msdElementTypeLine
                            tmpP = mPoint
                            tmpP.Z = mComplexStr.Current.AsLineElement.StartPoint.Z
                            tmpDist = Dist_Segment_to_Point(mComplexStr.Current.AsLineElement.StartPoint, mComplexStr.Current.AsLineElement.EndPoint, tmpP)
                                If tmpDist < minDist Then
                                minDist = tmpDist
                                Project_Point1 = Project_Point(mComplexStr.Current.AsLineElement.StartPoint, mComplexStr.Current.AsLineElement.EndPoint, tmpP)
                            End If
                    End Select
                Wend
    End Select
End Function
Private Function Dist_Segment_to_Point(StartPoint As Point3d, EndPoint As Point3d, iPoint As Point3d) As Double
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    Dim tmpL As LineElement
    vPoint = Vector3dSubtractPoint3dPoint3d(iPoint, StartPoint)
    vLine = Vector3dSubtractPoint3dPoint3d(EndPoint, StartPoint)
    
    c1 = Vector3dDotProduct(vPoint, vLine)
    c2 = Vector3dDotProduct(vLine, vLine)
        If c1 <= 0 Then
            Dist_Segment_to_Point = Point3dDistance(StartPoint, iPoint)
'            Set tmpL = CreateLineElement2(Nothing, StartPoint, iPoint)
'            ActiveModelReference.AddElement tmpL
'            tmpL.Redraw
        ElseIf c2 <= c1 Then
            Dist_Segment_to_Point = Point3dDistance(EndPoint, iPoint)
'            Set tmpL = CreateLineElement2(Nothing, EndPoint, iPoint)
'            ActiveModelReference.AddElement tmpL
'            tmpL.Redraw
        Else
            k = c1 / c2
            vProject = Vector3dScale(vLine, k)
            pProject = Vector3dAdd(Vector3dFromPoint3d(StartPoint), vProject)
            Dist_Segment_to_Point = Point3dDistance(Point3dFromVector3d(pProject), iPoint)
'            Set tmpL = CreateLineElement2(Nothing, Point3dFromVector3d(pProject), iPoint)
'            ActiveModelReference.AddElement tmpL
'            tmpL.Redraw
        End If
End Function
Private Function Project_Point(StartPoint As Point3d, EndPoint As Point3d, iPoint As Point3d) As Point3d
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    
    vPoint = Vector3dSubtractPoint3dPoint3d(iPoint, StartPoint)
    vLine = Vector3dSubtractPoint3dPoint3d(EndPoint, StartPoint)
    
    c1 = Vector3dDotProduct(vPoint, vLine)
    c2 = Vector3dDotProduct(vLine, vLine)
        If c1 <= 0 Then
            Project_Point = StartPoint
        ElseIf c2 <= c1 Then
            Project_Point = EndPoint
        Else
            k = c1 / c2
            vProject = Vector3dScale(vLine, k)
            Project_Point = Point3dFromVector3d(Vector3dAdd(Vector3dFromPoint3d(StartPoint), vProject))
        End If
End Function

Function GetClosestSegment3d(iLine As LineElement, iPoint As Point3d) As Point3d()
    Dim i As Long
    Dim Segment(0 To 1) As Point3d ' 0 - start , 1 - end
    i = iLine.GetClosestVertex(iPoint)
        If i = 0 Then
            Segment(0) = iLine.Vertex(1)
            Segment(1) = iLine.Vertex(2)
        ElseIf i = (iLine.VerticesCount - 1) Then
            Segment(0) = iLine.Vertex((iLine.VerticesCount) - 1)
            Segment(1) = iLine.Vertex(iLine.VerticesCount)
        Else
            i = i + 1
            If Dist_Segment_to_Point(iLine.Vertex(i), iLine.Vertex(i + 1), iPoint) >= Dist_Segment_to_Point(iLine.Vertex(i - 1), iLine.Vertex(i), iPoint) Then
                Segment(0) = iLine.Vertex(i - 1)
                Segment(1) = iLine.Vertex(i)
            Else
                Segment(0) = iLine.Vertex(i)
                Segment(1) = iLine.Vertex(i + 1)
            End If
        End If
    GetClosestSegment3d = Segment
    
End Function

Attribute VB_Name = "Module1"
Public CellName As Integer
Public RailAdd As Integer
Sub Main()
    UserForm_.Show vbModeless
End Sub

Attribute VB_Name = "PCE_Edit"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents

Private Sub IPrimitiveCommandEvents_Cleanup()

End Sub

Private Sub IPrimitiveCommandEvents_DataPoint(Point As Point3d, ByVal View As View)
    Dim myPoint As LineElement
    FindNerstVertex Point
End Sub

Private Sub IPrimitiveCommandEvents_Dynamics(Point As Point3d, ByVal View As View, ByVal DrawMode As MsdDrawingMode)
Dim rotation As Matrix3d
Dim transform As Transform3d
Dim myProfil As CellElement

rotation = Matrix3dInverse(View.rotation)
Set myProfil = CreateCellElement3(ActiveSettings.CellName, Point, True)
transform = Transform3dFromMatrix3dAndFixedPoint3d(rotation, myProfil.Origin)
myProfil.transform transform
myProfil.Redraw DrawMode

End Sub

Private Sub IPrimitiveCommandEvents_Keyin(ByVal Keyin As String)

End Sub

Private Sub IPrimitiveCommandEvents_Reset()
    CommandState.StartDefaultCommand
End Sub

Private Sub IPrimitiveCommandEvents_Start()
    CommandState.StartDynamics
End Sub

Private Sub FindNerstVertex(EndPoint As Point3d)
    Dim myEnum As ElementEnumerator
    Dim ComlexString As ElementEnumerator
    Dim myFilter As New ElementScanCriteria
    Dim i As Long
    Dim Rail As LineElement
    Dim minDistance As Double
    Dim tLineString As LineElement
    Dim j As Long
    Dim o As Long
    Dim movePoint As Point3d
    Dim tmpDist As Double
    
    
    minDistance = CDbl(UserForm_Settings.TextBox_tolerance.Text)
    
    myFilter.ExcludeAllTypes
    myFilter.IncludeType msdElementTypeLineString
    myFilter.IncludeType msdElementTypeComplexString
    
    If UserForm_Settings.TextBox_tolerance.Text <> "" Then
        myFilter.ExcludeAllLevels
        myFilter.IncludeLevel ActiveDesignFile.Levels.Find(UserForm_Settings.ComboBox_edit.Text)
    End If
        
    Set myEnum = ActiveModelReference.Scan(myFilter)
        While myEnum.MoveNext
            Select Case myEnum.Current.Type
                Case msdElementTypeLineString
                    tmpDist = DistancetoLine(myEnum.Current.AsLineElement, EndPoint)
                    If tmpDist < minDistance Then
                        If tmpDist > 0 Then
                            minDistance = tmpDist
                            Set Rail = myEnum.Current.AsLineElement
                        End If
                    End If
                Case msdElementTypeComplexString
                    Set ComlexString = myEnum.Current.AsComplexStringElement.GetSubElements
                        While ComlexString.MoveNext
                            Select Case ComlexString.Current.Type
                                Case msdElementTypeLineString
                                    tmpDist = DistancetoLine(ComlexString.Current.AsLineElement, EndPoint)
                                    If tmpDist < minDistance Then
                                        If tmpDist > 0 Then
                                            minDistance = tmpDist
                                            Set Rail = ComlexString.Current.AsLineElement
                                        End If
                                    End If
                            End Select
                        Wend
            End Select
        Wend
    If RailAdd = 1 Then
        InsertVertex Rail, EndPoint
    ElseIf RailAdd = 0 Then
        j = Rail.GetClosestVertex(EndPoint)
        Rail.ModifyVertex j, EndPoint
        Rail.Rewrite
        Rail.Redraw
    End If
End Sub

Private Function DistancetoLine(iLine As LineElement, iPoint As Point3d) As Double

    Dim vPoint As Vector3d
    Dim vLine As Vector3d
    Dim vProject As Vector3d
    Dim i As Long ' Индекс билжайшего вертекса
    Dim Segment As LineElement
    Dim ax As Double
    Dim ay As Double
    Dim az As Double
    Dim c1 As Double 'Скалярное произведение vPoint x vLine
    Dim c2 As Double 'Скалярное произведение vline x vLine
    Dim k As Double ' Коэффециент проекции
    Dim pProject As Point3d
    
    i = iLine.GetClosestSegment(iPoint)
    Set Segment = CreateLineElement2(Nothing, iLine.Vertex(i + 1), iLine.Vertex(i + 2))
    
    ax = iPoint.X - Segment.StartPoint.X
    ay = iPoint.Y - Segment.StartPoint.Y
    az = iPoint.Z - Segment.StartPoint.Z
    
    vPoint = Vector3dFromXYZ(ax, ay, az)
    
    ax = Segment.EndPoint.X - Segment.StartPoint.X
    ay = Segment.EndPoint.Y - Segment.StartPoint.Y
    az = Segment.EndPoint.Z - Segment.StartPoint.Z
    
    vLine = Vector3dFromXYZ(ax, ay, az)
    
    c1 = Vector3dDotProduct(vPoint, vLine)
    c2 = Vector3dDotProduct(vLine, vLine)
    
        If c1 <= 0 Then
            DistancetoLine = Point3dDistance(Segment.StartPoint, iPoint)
        ElseIf c2 <= c1 Then
            DistancetoLine = Point3dDistance(Segment.EndPoint, iPoint)
        ElseIf c1 = Segment.Length * Point3dDistance(iPoint, Segment.StartPoint) Then
            DistancetoLine = Point3dDistance(iPoint, iPoint)
        Else
            k = c1 / c2
            vProject = Vector3dScale(vLine, k)
            pProject.X = Segment.StartPoint.X + vProject.X
            pProject.Y = Segment.StartPoint.Y + vProject.Y
            pProject.Z = Segment.StartPoint.Z + vProject.Z
            DistancetoLine = Point3dDistance(pProject, iPoint)
        End If
    
'    Dim segment As LineElement
'    Dim i As Long ' Индекс билжайшего вертекса
'    Dim projectPoint As Point3d ' Проекция точки на сегмнет
'    Dim Perp As LineElement
'    Dim myPoint As LineElement
'
'    Set myPoint = CreateLineElement2(Nothing, iPoint, iPoint)
'    myPoint.Color = 3
'    myPoint.LineWeight = 8
'    ActiveModelReference.AddElement myPoint
'    myPoint.Redraw
'
'    i = iLine.GetClosestSegment(iPoint)
'        Set segment = CreateLineElement2(Nothing, iLine.Vertex(i + 1), iLine.Vertex(i + 2))
'        segment.Color = 3
'        segment.LineWeight = 4
'        ActiveModelReference.AddElement segment
'        projectPoint = segment.ProjectPointOnPerpendicular2(iPoint, Matrix3dIdentity)
'        DistancetoLine = Point3dDistance(projectPoint, iPoint)


End Function

Private Sub InsertVertex(iLine As LineElement, iPoint As Point3d)
    Dim i As Long
    i = iLine.GetClosestSegment(iPoint)
    iLine.InsertVertex i + 1, iPoint
    iLine.Rewrite
    iLine.Redraw
    
End Sub

Attribute VB_Name = "REplace"
Sub ReplaceCell()
    Dim myEnum As ElementEnumerator
    Dim myFilter As New ElementScanCriteria
    Dim MyCell As CellElement
    Dim myPoint As LineElement
    Dim lvl As Level
    
    If UserForm_Cell_to_Point.ComboBox_cell.Text = "" Then
        MsgBox "Выберите Cell"
    End If

    myFilter.ExcludeAllTypes
    myFilter.IncludeType msdElementTypeCellHeader
    
    Set myEnum = ActiveModelReference.Scan(myFilter)
    
    While myEnum.MoveNext
        Set MyCell = myEnum.Current
            If MyCell.Name = UserForm_Cell_to_Point.ComboBox_cell.Text Then
                Set myPoint = CreateLineElement2(MyCell, MyCell.Origin, MyCell.Origin)
                myPoint.Level = ActiveDesignFile.Levels.Find(ActiveSettings.Level.Name)
                ActiveModelReference.AddElement myPoint
                myPoint.Redraw
                    If UserForm_Cell_to_Point.CheckBox_delete_cell.Value = True Then
                        ActiveModelReference.RemoveElement MyCell
                        MyCell.Redraw
                    End If
            End If
    Wend
End Sub

Attribute VB_Name = "UserForm_"
Attribute VB_Base = "0{A01FF86E-44F7-44CB-9ACE-AAE12A7F2896}{279DF7AF-5A5F-424D-B689-30CBA31333A8}"
Attribute VB_GlobalNameSpace = False
Attribute VB_Creatable = False
Attribute VB_PredeclaredId = True
Attribute VB_Exposed = False
Attribute VB_TemplateDerived = False
Attribute VB_Customizable = False
Private Sub ComboBox_cell_DblClick(ByVal Cancel As MSForms.ReturnBoolean)
    Inizialisation.InizialisationCells
End Sub

Private Sub CommandButton_cell_to_line_Click()
    CommandState.StartLocate New LCE_Cell_to_Line
End Sub

Private Sub CommandButton_cie_Click()
    HookKey.HookKey
End Sub

Private Sub CommandButton_connect_Click()
    CommandState.StartLocate New LCE_Line_Snap
End Sub

Private Sub CommandButton_draw_point_Click()
    Draw_point.DrawPoint
End Sub

Private Sub CommandButton_edit_Click()
    CommandState.StartPrimitive New PCE_Edit, True
End Sub

Private Sub CommandButton_Rail_Add_Click()
    RailAdd = 1
    CommandState.StartPrimitive New PCE_Edit, True
End Sub

Private Sub CommandButton_Rail_L_Click()
    ActiveSettings.CellName = UserForm_Settings.ComboBox_Rail_Left.Text
    CadInputQueue.SendCommand "DIALOG CELLMAINTENANCE"
    CadInputQueue.SendCommand "PLACE CELL ICON"
End Sub

Private Sub CommandButton_Rail_move_Click()
    RailAdd = 0
    CommandState.StartPrimitive New PCE_Edit, True
End Sub

Private Sub CommandButton_Rail_R_Click()
    ActiveSettings.CellName = UserForm_Settings.ComboBox_Rail_Right.Text
    CadInputQueue.SendCommand "DIALOG CELLMAINTENANCE"
    CadInputQueue.SendCommand "PLACE CELL ICON"
End Sub

Private Sub CommandButton_replace_Click()
    ReplaceCell
    Inizialisation.InizialisationCells
End Sub

Private Sub CommandButton1_Click()
    CadInputQueue.SendReset
End Sub
Private Sub CommandButton_Settings_Click()
    UserForm_Settings.Show
End Sub
Private Sub UserForm_Initialize()
    'InizialisationCells
    UserFormIni
    IniLevels
End Sub
Private Sub UserFormIni()
    Dim myLevel As Level
    UserForm_Settings.ComboBox_level_line.Clear
    UserForm_Settings.ComboBox_level_point.Clear
    UserForm_Settings.ComboBox_edit.Clear
            For Each myLevel In ActiveModelReference.Levels
                UserForm_Settings.ComboBox_level_line.AddItem myLevel.Name
                UserForm_Settings.ComboBox_level_point.AddItem myLevel.Name
                UserForm_Settings.ComboBox_edit.AddItem myLevel.Name
            Next
 End Sub
 Private Sub IniLevels()
    Dim myLevel As Level
        UserForm_Settings.cmbLevels.Clear
            For Each myLevel In ActiveDesignFile.Levels
                UserForm_Settings.cmbLevels.AddItem myLevel.Name
            Next
End Sub

Attribute VB_Name = "UserForm_Settings"
Attribute VB_Base = "0{4A0E03ED-223F-4096-B759-9982583C701E}{AFA5BD9F-8370-45FB-8747-EA87AE926301}"
Attribute VB_GlobalNameSpace = False
Attribute VB_Creatable = False
Attribute VB_PredeclaredId = True
Attribute VB_Exposed = False
Attribute VB_TemplateDerived = False
Attribute VB_Customizable = False
Private Sub InizializeCell(myComboBox As ComboBox)
Dim MyCellEnum As CellInformationEnumerator
Dim MyCell As CellInformation
    myComboBox.Clear
    On Error GoTo EX
    Set MyCellEnum = Application.GetCellInformationEnumerator(False, False)
    While MyCellEnum.MoveNext
        Set MyCell = MyCellEnum.Current
        myComboBox.AddItem MyCell.Name
    Wend
EX:
inizialize_ListBox ListBox_levels
End Sub
Private Sub inizialize_ListBox(MyListBox As ListBox)
    Dim myLevel As Level
    Dim MyLevelName() As String
    ReDim MyLevelName(0)
    Dim MadeChange As Boolean
    Dim i As Integer
    Dim tmpName As String
    
        MyListBox.Clear
    For Each myLevel In ActiveDesignFile.Levels
        MyLevelName(UBound(MyLevelName)) = myLevel.Name
        ReDim Preserve MyLevelName(UBound(MyLevelName) + 1)
    Next
        ReDim Preserve MyLevelName(UBound(MyLevelName) - 1)
        
        MadeChange = True
        While MadeChange = True
            MadeChange = False
            For i = LBound(MyLevelName) To UBound(MyLevelName) - 1
                If StrComp(MyLevelName(i), MyLevelName(i + 1)) = 1 Then
                    tmpName = MyLevelName(i)
                    MyLevelName(i) = MyLevelName(i + 1)
                    MyLevelName(i + 1) = tmpName
                    MadeChange = True
                End If
            Next i
        Wend
        For i = LBound(MyLevelName) To UBound(MyLevelName)
            MyListBox.AddItem MyLevelName(i)
        Next i
End Sub


Private Sub CheckBox_useLevel_Change()
If CheckBox_useLevel.Value = True Then
    ListBox_levels.Enabled = True
ElseIf CheckBox_useLevel.Value = False Then
    ListBox_levels.Enabled = False
End If
End Sub



Private Sub cmbLevels_Change()
    UserForm_Cell_to_Point.CommandButton_cell_to_line.Enabled = True
End Sub

Private Sub ComboBox_edit_Change()
    UserForm_Cell_to_Point.CommandButton_Rail_Add.Enabled = True
    UserForm_Cell_to_Point.CommandButton_Rail_Move.Enabled = True
End Sub

Private Sub ComboBox_level_line_Change()
    UserForm_Cell_to_Point.CommandButton_draw_point.Enabled = True
End Sub

Private Sub ComboBox_Rail_Left_Change()
    UserForm_Cell_to_Point.CommandButton_Rail_L.Enabled = True
End Sub

Private Sub ComboBox_Rail_Left_DblClick(ByVal Cancel As MSForms.ReturnBoolean)
    InizializeCell UserForm_Settings.ComboBox_Rail_Left
End Sub

Private Sub ComboBox_Rail_Right_Change()
    UserForm_Cell_to_Point.CommandButton_Rail_R.Enabled = True
End Sub

Private Sub ComboBox_Rail_Right_DblClick(ByVal Cancel As MSForms.ReturnBoolean)
    InizializeCell UserForm_Settings.ComboBox_Rail_Right
End Sub

Private Sub UserForm_Initialize()
    InizializeCell UserForm_Settings.ComboBox_Rail_Left
    InizializeCell UserForm_Settings.ComboBox_Rail_Right
End Sub

Private Sub UserForm_QueryClose(Cancel As Integer, CloseMode As Integer)
    Cancel = 1
    UserForm_Settings.Hide
End Sub
