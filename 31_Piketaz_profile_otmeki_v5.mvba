Attribute VB_Name = "ComplexShapeToShape"
Option Explicit
Function ComplexShapeToShape(CShape As Element) As ShapeElement
    Dim MyEnum As ElementEnumerator
    Dim MyShape As ShapeElement
    Dim Verteces() As Point3d
    Dim i As Integer
    ReDim Verteces(0)
    If CShape.IsComplexShapeElement Then
        Set MyEnum = CShape.AsComplexShapeElement.GetSubElements
            While MyEnum.MoveNext
                For i = 0 To UBound(MyEnum.Current.AsVertexList.GetVertices)
                    Verteces(UBound(Verteces)) = MyEnum.Current.AsLineElement.Vertex(i + 1)
                    ReDim Preserve Verteces(UBound(Verteces) + 1)
                Next i
                ReDim Preserve Verteces(UBound(Verteces) - 1)
            Wend
     '   CShape.IsSnappable = True
        Set MyShape = CreateShapeElement1(CShape, Verteces, msdFillModeNotFilled)
        MyShape.IsSnappable = True
        Set ComplexShapeToShape = MyShape
    ElseIf CShape.IsShapeElement Then
        Set ComplexShapeToShape = CShape.AsShapeElement
    End If
End Function

Attribute VB_Name = "LCE_SetCorridor"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private SelElement As Element


Private Sub ILocateCommandEvents_Accept(ByVal Element As Element, Point As Point3d, ByVal View As View)
    Dim i As Long
    Dim indexBox As Long
    
    indexBox = 1
    
    For i = 0 To UBound(PiketLine)
        CutShape SelElement, PiketLine(i).AsLineElement, indexBox
    Next i
    Erase PiketLine
End Sub

Private Sub ILocateCommandEvents_Cleanup()

End Sub

Private Sub ILocateCommandEvents_Dynamics(Point As Point3d, ByVal View As View, ByVal DrawMode As MsdDrawingMode)

End Sub

Private Sub ILocateCommandEvents_LocateFailed()

End Sub

Private Sub ILocateCommandEvents_LocateFilter(ByVal Element As Element, Point As Point3d, Accepted As Boolean)
    Accepted = False
    If Element.IsShapeElement Or Element.IsComplexShapeElement Then
        Set SelElement = Element
        Accepted = True
    End If
End Sub

Private Sub ILocateCommandEvents_LocateReset()
    CommandState.StartDefaultCommand

End Sub

Private Sub ILocateCommandEvents_Start()

End Sub

Private Sub CutShape(ByRef IniShape As Element, CutLine As LineElement, index As Long)
    Dim iPoint() As Point3d ' Точки пересечения
    Dim Seg1 As Long
    Dim Seg2 As Long
    Dim intPoint1 As Point3d
    Dim intPoint2 As Point3d
    Dim Vertex1() As Point3d
    Dim Vertex2() As Point3d
    Dim Shape1 As ShapeElement
    Dim Shape2 As ShapeElement
    Dim tmpShape As ShapeElement
    Dim i As Integer
    Dim j As Integer
    
'    Dim mEnum As ElementEnumerator
'    Dim mElements() As Element
'    ReDim mElements(1)
    
    j = 1
    
    iPoint = IniShape.AsIntersectableElement.GetIntersectionPoints(CutLine, Matrix3dIdentity)
    
        If UBound(iPoint) = 1 Then
            If IniShape.IsShapeElement Or IniShape.IsComplexShapeElement Then
'                Set mElements(0) = CutLine
'                Set mElements(1) = IniShape
'                Set mEnum = GetIntersectionShapesFromRegion(mElements, Nothing, msdFillModeNotFilled)
'
                Set tmpShape = ComplexShapeToShape.ComplexShapeToShape(IniShape)
                  ReDim Vertex1(0)
                  ReDim Vertex2(0)
                  If tmpShape.GetClosestSegment(iPoint(0)) > tmpShape.GetClosestSegment(iPoint(1)) Then
                      Seg1 = tmpShape.GetClosestSegment(iPoint(1))
                      intPoint1 = iPoint(1)
                      Seg2 = tmpShape.GetClosestSegment(iPoint(0))
                      intPoint2 = iPoint(0)
                  ElseIf tmpShape.GetClosestSegment(iPoint(0)) < tmpShape.GetClosestSegment(iPoint(1)) Then
                      Seg1 = tmpShape.GetClosestSegment(iPoint(0)) + 1
                      intPoint1 = iPoint(0)
                      Seg2 = tmpShape.GetClosestSegment(iPoint(1)) + 1
                      intPoint2 = iPoint(1)
                  End If
                      
                  For i = 0 To (Seg1 - 1)
                      Vertex1(i) = tmpShape.Vertex(i + 1)
                      ReDim Preserve Vertex1(UBound(Vertex1) + 1)
                  Next i
                      Vertex1(Seg1) = intPoint1
                      ReDim Preserve Vertex1(UBound(Vertex1) + 1)
                      Vertex1(Seg1 + 1) = intPoint2
                      ReDim Preserve Vertex1(UBound(Vertex1) + 1)
                      
                  For i = (Seg2 + 1) To tmpShape.VerticesCount
                      Vertex1(UBound(Vertex1)) = tmpShape.Vertex(i)
                      ReDim Preserve Vertex1(UBound(Vertex1) + 1)
                  Next i
                      ReDim Preserve Vertex1(UBound(Vertex1) - 1)
                      
        ''''''''''''''''''''''''''''''''''''''''''''''''''''''''''''''''' второй конту
                  Vertex2(0) = intPoint1
                  ReDim Preserve Vertex2(j)
                  For i = (Seg1 + 1) To Seg2
                      Vertex2(j) = tmpShape.Vertex(i)
                      j = j + 1
                      ReDim Preserve Vertex2(j)
                  Next i
                      Vertex2(j) = intPoint2
                  Set Shape1 = CreateShapeElement1(tmpShape, Vertex1(), msdFillModeNotFilled)
                  ActiveModelReference.AddElement Shape1
                  Shape1.Redraw
                  Set Shape2 = CreateShapeElement1(tmpShape, Vertex2(), msdFillModeNotFilled)
                  ActiveModelReference.AddElement Shape2
                  Shape2.Redraw
                  
                Dim iShape As Element
                Dim nameShape As ShapeElement
                
                If Shape1.Area > Shape2.Area Then
                    Set iShape = Shape1
                    Set nameShape = Shape2

                Else
                    Set iShape = Shape2
                    Set nameShape = Shape1
                End If
'                Set iShape = Shape2
'                Set nameShape = Shape1
                DrawNameOfBox nameShape, index
                index = index + 1
                ActiveModelReference.RemoveElement IniShape
                IniShape.Redraw
                Set IniShape = iShape
            End If
        End If
    Erase iPoint
End Sub

Private Sub DrawNameOfBox(mBox As ShapeElement, index As Long)
    Dim mName As TextElement
    
    ActiveSettings.TextStyle.Font = ActiveDesignFile.Fonts("Arial")
    ActiveSettings.TextStyle.Height = CDbl(MyForm.tbPik.Text) * 0.1
    ActiveSettings.TextStyle.Width = CDbl(MyForm.tbPik.Text) * 0.1
    ActiveSettings.TextStyle.Justification = msdTextJustificationCenterCenter
    
    Set mName = CreateTextElement1(Nothing, MyForm.TextBox_PrefBoxName.Text & Format(CStr(index), MyForm.ComboBox_razryd.Text), mBox.Centroid, Matrix3dIdentity)
    
    ActiveModelReference.AddElement mName
    mName.Redraw
    
End Sub

Attribute VB_Name = "Module1"
Option Explicit


Public PiketLine() As Element
Public RotatePiket As Boolean


Sub main()
    MyForm.Show vbModeless
End Sub

 Sub DrawProfilePoint(mProfile As LineElement, mRot As Double)
    Dim MyEnum As ElementEnumerator
    Dim mStructLineTemp() As Element
    
    Dim mStructLine() As Element
    ReDim mStructLine(0)
    Dim i As Long ' Счетчик структурных линий
    Dim j As Long ' Счетчик пересечений
    Dim mPoint As LineElement ' Точка пересечения
    Dim pPoint() As Point3d
    Dim allPoints() As Point3d
    Dim mBoundary() As Element
    Dim mCell As CellElement
    
    Set MyEnum = ActiveModelReference.GetSelectedElements
    mStructLineTemp = MyEnum.BuildArrayFromContents
  ' If UBound(mStructLineTemp) >= 0 Then
  On Error Resume Next
        For i = 0 To UBound(mStructLineTemp)
             If (mStructLineTemp(i).Level.Name <> MyForm.ComboBox_Levels.Text And mStructLineTemp(i).Level.Name <> MyForm.ComboBoxLevelProfile.Text) Or MyForm.CheckBox_pik_by_centrline.Value = True Then
                 Set mStructLine(UBound(mStructLine)) = mStructLineTemp(i)
                 ReDim Preserve mStructLine(UBound(mStructLine) + 1)
             End If
        Next i
        ReDim Preserve mStructLine(UBound(mStructLine) - 1)
         For i = 0 To UBound(mStructLine)
                 pPoint = mStructLine(i).AsIntersectableElement.GetIntersectionPoints(mProfile, Matrix3dIdentity)
                     If UBound(pPoint) <> -1 Then
                     ArrayAddArray allPoints, pPoint
                     
                         For j = 0 To UBound(pPoint)
                         If MyForm.CheckBox_AddVertex Then AddVertexToElement mStructLine(i), pPoint(j)
                             If MyForm.CheckBox_placeCell.Value = True And MyForm.ComboBox_cell.Text <> "" Then
                                 Set mCell = CreateCellElement3(MyForm.ComboBox_cell.Text, pPoint(j), True)
                                 Rotate mCell, pPoint(j), mRot
                                 mCell.Level = CheckLevel(MyForm.ComboBoxLeveOfPiket.Text)
                                 ActiveModelReference.AddElement mCell
                                 mCell.Redraw
                             Else
                                 Set mPoint = CreateLineElement2(Nothing, pPoint(j), pPoint(j))
                                 mPoint.LineWeight = 5
                                 mPoint.Level = CheckLevel(MyForm.ComboBoxLeveOfPiket.Text)
                                 ActiveModelReference.AddElement mPoint
                                 mPoint.Redraw
                             End If
                            ' DrawTxt pPoint(j), mRot
                         Next j
                     End If
         Next i
         SortingPoints allPoints, mProfile
         PlaceTextElevation mBoundary, allPoints, mRot
 '   Else: MsgBox "Регионы не выделены"
 '   End If
End Sub

Private Sub AddVertexToElement(ByRef mElement As Element, mPoint As Point3d)

Dim i As Long
Dim mVertexes() As Point3d
Dim key As Boolean

mVertexes = mElement.AsVertexList.GetVertices

key = True
For i = 0 To mElement.AsVertexList.VerticesCount - 1
    If Point3dEqual(mVertexes(i), mPoint) Then key = False
Next i

If key Then

    mElement.AsVertexList.InsertVertex (mElement.AsVertexList.GetClosestSegment(mPoint) + 1), mPoint
    mElement.Redraw msdDrawingModeNormal
    mElement.Rewrite
    
End If

End Sub

 Function CheckLevel(LevelName As String) As Level
    Dim MyLevel As Level
    On Error Resume Next
    
    Set CheckLevel = ActiveDesignFile.Levels(LevelName)
    If Err.Number <> 0 And LevelName <> "" Then
         Set MyLevel = ActiveDesignFile.AddNewLevel(LevelName)
         ActiveDesignFile.Levels.Rewrite
         MsgBox "Создан слой: " & LevelName
         Set CheckLevel = MyLevel
    End If
    Err.Clear
End Function
Private Sub ArrayAddArray(ByRef mArray() As Point3d, AddArray() As Point3d)
    Dim i As Long
    Dim u As Long
    
    If UBound(AddArray) = -1 Then
        Exit Sub
    Else
        On Error Resume Next
        u = UBound(mArray) + 1
        If Err.Number = 9 Then
            ReDim mArray(0)
            u = 0
        End If
        Err.Clear
        For i = 0 To UBound(AddArray)
            ReDim Preserve mArray(u + i)
            mArray(u + i) = AddArray(i)
        Next i
    End If
End Sub
Private Sub SortingPoints(ByRef mPoints() As Point3d, mLine As LineElement)
    Dim StartPoint As Point3d
    Dim i As Long, j As Long
    Dim tPoint As Point3d
    Dim fontHeight As Double
        
    If mLine.endPoint.Y > mLine.StartPoint.Y Then
        StartPoint = mLine.endPoint
    Else
        StartPoint = mLine.StartPoint
    End If
    
    fontHeight = CDbl(MyForm.TextBox_TextHeight.Text)
    
    If UBound(mPoints) > 0 Then
        For i = 0 To UBound(mPoints)
            For j = 0 To UBound(mPoints)
                If j <> i Then
                    If Point3dDistanceXY(StartPoint, mPoints(j)) > Point3dDistanceXY(StartPoint, mPoints(i)) Then
                        tPoint = mPoints(i)
                        mPoints(i) = mPoints(j)
                        mPoints(j) = tPoint
                    End If
                End If
            Next j
        Next i
    Else: Exit Sub
    End If
End Sub
Private Sub PlaceTextElevation(ByRef mBounds() As Element, mPoints() As Point3d, rAngle As Double)
    Dim l As Long, u As Long
    Dim i As Long
    Dim j As Integer
    Dim tBoundary As ShapeElement   ' Контур текста
    Dim tElev As TextElement
    Dim mEnum As ElementEnumerator
    Dim H As Double, W As Double
    
    H = CDbl(MyForm.TextBox_TextHeight.Text) + CDbl(MyForm.TextBox_offsetY.Text)
    u = UBound(mPoints)
    On Error Resume Next
    l = UBound(mBounds) + 1
    If Err.Number = 9 Then
        ReDim mBounds(0)
        l = 0
    End If
    Err.Clear
    
    For i = 0 To u
        CreateTextElevation tElev, mPoints(i), ActiveDesignFile.Levels(MyForm.ComboBoxLeveOfPiket.Text), rAngle
        Rotate tElev, mPoints(i), rAngle
        MoveElement tElev, mPoints(i), rAngle, W, H, 0
        Set tBoundary = ShapeFromText(tElev)
'        ActiveModelReference.AddElement tBoundary
'        tBoundary.Redraw
        Select Case MyForm.ComboBoxJustification.Value
            Case "Right Top"
               ' MoveElement tElev, mPoints(i), rAngle, 0, CDbl(MyForm.TextBox_offsetX.Text)
               MoveElement tElev, mPoints(i), rAngle, W, H, 2
            Case "Right Center"
               ' MoveElement tElev, mPoints(i), rAngle, H * -0.5, CDbl(MyForm.TextBox_offsetX.Text)
               'MoveElement tElev, mPoints(i), rAngle, W, H, j
            Case "Right Bottom"
               ' MoveElement tElev, mPoints(i), rAngle, H * -1, CDbl(MyForm.TextBox_offsetX.Text)
               MoveElement tElev, mPoints(i), rAngle, W, H, 1
            Case "Best Position"
                ReDim Preserve mBounds(l + i)
                W = Point3dDistance(tBoundary.Vertex(1), tBoundary.Vertex(4))
                If i = 0 Then
                    MoveElement tBoundary, mPoints(i), rAngle, W, H, 8
                    MoveElement tElev, mPoints(i), rAngle, W, H, 8
                    Set mBounds(l + i) = tBoundary
                Else
                    If i = u Then
                        MoveElement tBoundary, mPoints(i), rAngle, W, H, 9
                        MoveElement tElev, mPoints(i), rAngle, W, H, 9
                    End If
                    For j = 1 To 7
                        MoveElement tBoundary, mPoints(i), rAngle, W, H, j
                        MoveElement tElev, mPoints(i), rAngle, W, H, j
                        Set mEnum = tBoundary.GetIntersectionShapesFromRegion(mBounds, Nothing)
                            If getEnumeratorCount(mEnum) = 0 Then
                                Set mBounds(l + i) = tBoundary
                                Exit For
                            End If
                    If j = 7 Then Set mBounds(l + i) = tBoundary
                    Next j
                End If
        End Select
    ActiveModelReference.AddElement tElev
    tElev.Redraw
    Next i
End Sub
Function getEnumeratorCount(oEnumerator As ElementEnumerator) As Long
    Dim count As Long
    With oEnumerator
        .Reset
        Do While .MoveNext
            count = count + 1
        Loop
        .Reset
    End With
    getEnumeratorCount = count
End Function
Private Sub CreateTextElevation(ByRef mText As Element, mPoint As Point3d, mLevel As Level, mAngle)
    
    Set mText = CreateTextElement1(Nothing, FormatNumber(Round(mPoint.Z, 2), 2, vbTrue, vbTrue, vbFalse), mPoint, Matrix3dIdentity)
    mText.AsTextElement.TextStyle.Height = CDbl(MyForm.TextBox_TextHeight.Text)
    mText.AsTextElement.TextStyle.Width = CDbl(MyForm.TextBox_TextWidth.Text)
    mText.AsTextElement.TextStyle.Font = ActiveDesignFile.Fonts(MyForm.ComboBox_Fonts.Text)
    mText.AsTextElement.TextStyle.Justification = msdTextJustificationLeftBottom
    mText.Level = mLevel
    
End Sub
Private Sub Rotate(ByRef mElem As Element, tPoint As Point3d, mAngle As Double)
  '  Debug.Print "ДО поворота 1: " & GetAngleTxt(mElem.AsTextElement)
    mElem.RotateAboutZ tPoint, mAngle
  '  Debug.Print "После поворота 1: " & GetAngleTxt(mElem.AsTextElement)
    mElem.Rewrite
  '  Debug.Print "После поворота 1 Rewrite: " & GetAngleTxt(mElem.AsTextElement)
End Sub
Private Sub MoveElement(ByRef mElem As Element, tPoint As Point3d, mAngle As Double, W As Double, H As Double, mPosition As Integer)
    Dim Offset As Double
    
    Offset = CDbl(MyForm.TextBox_offsetX.Text)
    
    mElem.RotateAboutZ tPoint, ((2 * Pi) - mAngle)
    Select Case mPosition
        Case 0
            mElem.Move Point3dFromXYZ(Offset, H * -0.5, 0)
        Case 1
            'mElem.Move Point3dFromXYZ(0, H * -0.5, 0)
        Case 2
            mElem.Move Point3dFromXYZ(-(2 * Offset + W), 0, 0)
        Case 3
            'mElem.Move Point3dFromXYZ(0, H * -1, 0)
        Case 4
            mElem.Move Point3dFromXYZ((2 * Offset + W), H * 0.5, 0)
        Case 5
            mElem.Move Point3dFromXYZ(-(2 * Offset + W), 0, 0)
        Case 6
            mElem.Move Point3dFromXYZ(0, H * -1, 0)
        Case 7
            mElem.Move Point3dFromXYZ((2 * Offset + W), 0, 0)
        Case 8
            mElem.Move Point3dFromXYZ(0, H * 0.5, 0)
        Case 9
            mElem.Move Point3dFromXYZ(0, H * -0.5, 0)
        End Select
    'mElem.Move Point3dFromXYZ(H, V, 0)
    
    mElem.RotateAboutZ tPoint, mAngle
End Sub
Private Function ShapeFromText(ByVal mText As TextElement) As ShapeElement
    Dim tRotation As Double
    Dim p(0 To 3) As Point3d
    Dim sBoundary As Range3d
    Dim mBoundary As ShapeElement
    Dim mTransform As Transform3d
       
    tRotation = GetAngleTxt(mText)
    If tRotation <> 0 Then mText.RotateAboutZ mText.Origin, 2 * Pi - tRotation 'Поворачивает текст в горизонталь
    
    sBoundary = mText.Boundary
    p(0).X = sBoundary.Low.X
    p(0).Y = sBoundary.Low.Y
    p(1).X = sBoundary.Low.X
    p(1).Y = sBoundary.High.Y
    p(2).X = sBoundary.High.X
    p(2).Y = sBoundary.High.Y
    p(3).X = sBoundary.High.X
    p(3).Y = sBoundary.Low.Y
    
    Set mBoundary = CreateShapeElement1(Nothing, p)
    mBoundary.RotateAboutZ mText.Origin, tRotation
'    mTransform = Transform3dFromMatrix3dAndFixedPoint3d(mText.Rotation, mText.Origin)
'    mBoundary.Transform mTransform
'    ActiveModelReference.AddElement mBoundary
'    mBoundary.Redraw
    mText.RotateAboutZ mText.Origin, tRotation
    Set ShapeFromText = mBoundary
End Function
Function GetAngleTxt(mTxt As TextElement) As Double
    Dim rotationX As Double
    Dim rotationY As Double
    Dim rotationZ As Double
    Dim scaleFactor As Double
    
    If (Matrix3dIsXRotationYRotationZRotationScale(mTxt.Rotation, rotationX, rotationY, rotationZ, scaleFactor)) Then
            GetAngleTxt = rotationZ
    End If
End Function
Private Function ProcessPointsSingl(ByRef mPoints() As Point3d) As Variant
    Dim pointExtent As Long, textExtent As Long
    Dim outPoints() As Point3d
    ReDim outPoints(0)
    Dim i As Long
    
    pointExtent = Point3dDistanceXY(mPoints(0), mPoints(UBound(mPoints)))
    textExtent = (UBound(mPoints) - 1) * fontHeight
    
    If (textExtent - pointExtent) > 0 Then
        For i = 0 To outPoints(UBound(outPoints))
            ReDim Preserve outPoints(i)
            outPoints(UBound(outPoints)) = CreatePointByDistance(mPoints(0), mPoints(1), (pointExtent - textExtent) * 0.5 + CDbl(MyForm.TextBox_TextHeight.Text) * i)
            outPoints(UBound(outPoints)).Z = mPoints(i).Z
        Next i
        ProcessPoints = outPoints
    Else
        ProcessPointsMulty mPoints
    End If
End Function
'Private Function ProcessPointsMulty(ByRef mPoints() As Point3d) As Variant
'    Dim s As Long, e As Long
'    Dim i As Long
'    Dim fHeight As Double
'
'    fHeight = CDbl(MyForm.TextBox_TextHeight.Text)
'
'    For i = 0 To (UBound(mPoints) - 1)
'        If Point3dDistanceXY(mPoints(i), mPoints(i + 1)) < fHeight Then
'            s = s
'            e = e + 1
'        Else
'            If Point3dDistanceXY(mPoints(s), mPoints(e + 1)) < (fHeight * (e - s) + 1) Then
'                s = s
'                e = e + 1
'            Else
'                s = e
'
'            End If
'        End If
'    Next
'End Function

'Private Sub ProcessPointsMulty(inPoints() As Point3d, outPoints() As Point3d, s As Long, e As Long)
'    Dim i As Long
'    Dim fHeight As Double
'
'    fHeight = CDbl(MyForm.TextBox_TextHeight.Text)
'    e = s
'    For i = s To UBound(inPoint)
'        If Point3dDistanceXY(inPoints(i), inPoints(i + 1)) < fHeight Then
'            s = s
'            e = e + 1
'        Else
'            If Point3dDistanceXY(mPoints(s), mPoints(e + 1)) < (fHeight * (e - s) + 1) Then
'                s = s
'                e = e + 1
'            Else
'                For i = 0 To s
'                    ReDim Preserve outPoints(i + s)
'                        outPoints(ubound(outPoints))=
'
'
'                Next i
'        End If
'    Next i
'End Sub

Private Function CreatePointByDistance(pStart As Point3d, pEnd As Point3d, Offset As Double) As Point3d

    Dim vOs As Vector3d
    
    vOs = Vector3dFromPoint3d(Point3dSubtract(pEnd, pStart))
    vOs = Vector3dScale(Vector3dNormalize(vOs), Offset)
    
    CreatePointByDistance = Point3dFromVector3d(vOs)
    
End Function

Sub DrawTxt(oPoint As Point3d, mRotation As Double)
    Dim mText As TextElement
    Dim tTransform As Transform3d
    Dim tPoint As Point3d
    
    tPoint.X = oPoint.X + CDbl(MyForm.TextBox_offsetX.Text)
    tPoint.Y = oPoint.Y + CDbl(MyForm.TextBox_offsetY.Text)
    tPoint.Z = oPoint.Z
    
    Set mText = CreateTextElement1(Nothing, FormatNumber(Round(CStr(oPoint.Z), 2), 2, vbTrue, vbTrue, vbFalse), tPoint, Matrix3dIdentity)
    mText.TextStyle.Height = CDbl(MyForm.TextBox_TextHeight.Text)
    mText.TextStyle.Width = CDbl(MyForm.TextBox_TextWidth.Text)
    mText.TextStyle.Font = ActiveDesignFile.Fonts(MyForm.ComboBox_Fonts.Text)
    mText.TextStyle.Justification = msdTextJustificationLeftBottom
    mText.RotateAboutZ oPoint, mRotation
    ActiveModelReference.AddElement mText
    mText.Redraw
End Sub

Function AngleTxt(pSt As Point3d, pEnd As Point3d) As Double
Dim dAng As Double
Dim Angle As Double
Dim ang As Double
Dim dx As Double
Dim dy As Double
dx = pEnd.X - pSt.X
dy = pEnd.Y - pSt.Y
If dy <> 0 Then
    ang = Atn(dx / dy)
    If dx >= 0 And dy > 0 Then
        dAng = ang
    ElseIf dx >= 0 And dy < 0 Then
        dAng = ang + Pi
    ElseIf dx < 0 And dy < 0 Then
        dAng = ang + Pi
    ElseIf dx < 0 And dy > 0 Then
        dAng = ang + 2 * Pi
    End If
ElseIf dy = 0 Then

    If dx > 0 Then
        dAng = Pi / 2
    ElseIf dx < 0 Then
        dAng = 3 * Pi / 4
    End If
End If
Angle = Pi / 2 - dAng

'************* Убрать кавычки для того, что бы автоматом разворачивались подписи
'--------------------------------------------------------------------------
    If MyForm.CheckBox_rotation.Value = True Then
        If Angle > Pi * 0.5 And Angle < Pi * 1.5 Then
            Angle = Angle + Pi
            RotatePiket = True
        End If
        If Angle > -Pi * 1.5 And Angle < -Pi * 0.5 Then
            Angle = Angle + Pi
            RotatePiket = True
        End If
    End If
AngleTxt = Angle

End Function

Attribute VB_Name = "MyForm"
Attribute VB_Base = "0{9A2BD9A1-57FB-42F3-B209-33904A41932B}{50421480-5B9D-45E5-9588-1F6353D5DF59}"
Attribute VB_GlobalNameSpace = False
Attribute VB_Creatable = False
Attribute VB_PredeclaredId = True
Attribute VB_Exposed = False
Attribute VB_TemplateDerived = False
Attribute VB_Customizable = False
Option Explicit

Private Sub InitializeLevels(mComboBox As ComboBox)
    Dim MyLevel As Level
    
    mComboBox.Clear
    For Each MyLevel In ActiveDesignFile.Levels
        mComboBox.AddItem MyLevel.Name
    Next
End Sub

Private Sub btnCreate_Click()
Dim piket() As Point3d
Dim MyLineVert() As Point3d ' Вертексы линии
Dim i As Long
Dim k As Double
Dim V As Double ' Количество вертексов в искомой линии
Dim j As Double 'Количество пикетов
Dim A As Double
Dim Point As LineElement
Dim pik As Double   'Расстояние между пикетами
Dim lineEnum As ElementEnumerator
Dim MyEnum As ElementEnumerator
Dim mFilter As New ElementScanCriteria
Dim MyLine As LineElement
Dim MyLine3D As LineElement

Dim vLine As Vector3d   ' Вектор отрезка
Dim vPiket As Vector3d  ' Вектор пикета
Dim p1 As Point3d   'Начальная точка пикета
Dim p2 As Point3d   'Конечная точка пикета
Dim l As Double   'Накопленная длинна пикетов
Dim s As Double   'НАкопленная длина отрезков линии
Dim D As Double   'Длина отрезка
Dim MyTxt As TextElement    'Подпись пикета
Dim RotationMatrix As Matrix3d
Dim rOtmetki As Double
Dim mLine() As Element
Dim ArrlineEnum() As Element

ReDim piket(0)

j = 0
pik = CDbl(tbPik.Text)
D = CDbl(tbD.Text)

Set MyEnum = ActiveModelReference.GetSelectedElements
i = 0
While MyEnum.MoveNext
    Select Case MyEnum.Current.Type
        Case msdElementTypeLineString
            If MyEnum.Current.Level.Name = MyForm.ComboBox_Levels.Text Then
            ReDim Preserve mLine(i)
                Set mLine(i) = MyEnum.Current
                i = i + 1
            End If
    End Select
Wend
ArrlineEnum = mLine
If i = 0 Then
    mFilter.ExcludeAllTypes
    mFilter.ExcludeAllLevels
    
    mFilter.IncludeLevel ActiveDesignFile.Levels(MyForm.ComboBox_Levels.Text)
    mFilter.IncludeType msdElementTypeLineString
    mFilter.IncludeType msdElementTypeComplexString

    Set lineEnum = ActiveModelReference.Scan(mFilter)
    ArrlineEnum = lineEnum.BuildArrayFromContents
End If
    
    For A = 0 To UBound(ArrlineEnum)
        Select Case ArrlineEnum(A).Type
            Case msdElementTypeLineString
            ReDim piket(0)
            j = 0
                Set MyLine = ArrlineEnum(A)
                'Set MyLine3D = MyLine
                
                If MyForm.CheckBox_Piket2D Then
                    MyLine.Transform Transform3dFromMatrix3dPoint3d(Matrix3dFromScaleFactors(1, 1, 0), Point3dFromXYZ(0, 0, 0)) ''''' Линия в 2D
                End If
                If cbxRevers.Value = True Then Set MyLine = ReversLine(MyLine)
                j = MyLine.Length \ pik
                    If MyLine.Length > pik * j Then
                        For i = 1 To j
                            ReDim Preserve piket(UBound(piket) + 1)
                            piket(i) = MyLine.PointAtDistance(pik * (i))
                        Next i
                         '   ReDim Preserve Piket(UBound(Piket) - 1)
                    ElseIf MyLine.Length < pik * j Then
                         For i = 1 To j - 1
                            ReDim Preserve piket(UBound(piket) + 1)
                            piket(i) = MyLine.PointAtDistance(pik * (i))
                        Next i
                    ElseIf MyLine.Length < pik Then
                        piket(0) = MyLine.PointAtDistance(MyLine.Length * 0.5)
                    End If
                Dim Xmod As Boolean
                
                For k = 1 To UBound(piket)
                    RotatePiket = False
                    Xmod = True
                    If TextBoxXmod.Text = "0" Then
                        Xmod = True
                    Else
                        If k Mod CDbl(TextBoxXmod.Text) = 0 Then
                            Xmod = False
                        End If
                    End If
                    If Xmod Then
                        vPiket = CreatePiketVector(MyLine, piket(k), i)
                        p1 = Point3dAddPoint3dVector3d(piket(k), vPiket)
                        vPiket = Vector3dScale(vPiket, -1)
                        p2 = Point3dAddPoint3dVector3d(piket(k), vPiket)
                        Set Point = CreateLineElement2(Nothing, p1, p2)
                        RedimPreserve PiketLine
                        Set PiketLine(UBound(PiketLine)) = Point
                            If CheckBox_piket.Value = True Then ' Ставить пикетаж
                                Point.Level = Module1.CheckLevel(MyForm.ComboBoxLevelOfPiketaz.Text)
                                ActiveModelReference.AddElement Point
                                Point.Redraw
                            End If
                        Dim textPiketaz As String
                        textPiketaz = CStr(k) * CDbl(tbPik.Text) & TextBox_piketazPostfix.Text
                        If CheckBox_ModPiketaz Then
                            textPiketaz = (CStr(k) * CDbl(tbPik.Text) - (k * CDbl(tbPik.Text) \ 100) * 100) & TextBox_piketazPostfix.Text
                        End If
                        If cbxReturn.Value = True Then
                            rOtmetki = AngleTxt(MyLine.Vertex(i + 1), MyLine.Vertex(i + 2)) + Pi
                            RotationMatrix = Matrix3dFromAxisAndRotationAngle(2, rOtmetki)
                            If Not RotatePiket Then ' Разворот пикетажа
                                Set MyTxt = CreateTextElement1(Nothing, textPiketaz, p2, RotationMatrix) '
                            Else
                                Set MyTxt = CreateTextElement1(Nothing, textPiketaz, p1, RotationMatrix) '
                            End If
                        Else
                            rOtmetki = AngleTxt(MyLine.Vertex(i + 1), MyLine.Vertex(i + 2))
                            RotationMatrix = Matrix3dFromAxisAndRotationAngle(2, rOtmetki)
                            If Not RotatePiket Then ' Разворот пикетажа
                                Set MyTxt = CreateTextElement1(Nothing, textPiketaz, p1, RotationMatrix) '
                            Else
                                Set MyTxt = CreateTextElement1(Nothing, textPiketaz, p2, RotationMatrix) '
                            End If
                                
                        End If
                                Module1.DrawProfilePoint Point, rOtmetki
                            If CheckBox_textPiket.Value = True Then ' Подписи пикетов
                                MyTxt.TextStyle.Justification = msdTextJustificationCenterBottom
                                MyTxt.Level = Module1.CheckLevel(MyForm.ComboBoxLevelOfPiketaz.Text)
                                ActiveModelReference.AddElement MyTxt
                                MyTxt.Redraw
                            End If
                        Xmod = True
                    End If
                Next k
        End Select
    Next A
End Sub


Private Function GetIntersection(mLineString As LineElement, mLine As LineElement) As Point3d
    Dim pPoint() As Point3d
    
    pPoint = mLineString.AsIntersectableElement.GetIntersectionPoints(mLine, Matrix3dIdentity)
    If UBound(pPoint) <> -1 Then
        GetIntersection = pPoint(0)
    End If
End Function
Private Function CreatePiketVector(mLine As LineElement, mPiket As Point3d, iSegment As Long) As Vector3d

    Dim Ax As Double, Ay As Double, Az As Double
    Dim vPiket As Vector3d
    Dim vLine As Vector3d
    Dim vBissectrisa As Vector3d
    Dim iVertex As Long
    Dim k As Double
    
    iSegment = mLine.GetClosestSegment(mPiket)
    iVertex = mLine.GetClosestVertex(mPiket)
    
    Ax = mLine.Vertex(iSegment + 2).X - mPiket.X
    Ay = mLine.Vertex(iSegment + 2).Y - mPiket.Y
    
    If Ax = 0 And Ay = 0 Then
        Ax = mLine.Vertex(iSegment + 3).X - mPiket.X
        Ay = mLine.Vertex(iSegment + 3).Y - mPiket.Y
    End If
    
    vLine = Vector3dFromXY(Ax, Ay)
    vPiket = Vector3dUnitPerpendicularXY(vLine)
    
    k = CDbl(MyForm.tbPik.Text) * CDbl(MyForm.TextBox_BissectrisaTolerance.Text)
    If CheckBox_AngleTolerance.Value Then
        k = k * GetAngleBetweenTwoVerctors(mLine, iVertex)
    End If
'    If Point3dDistance(mPiket, mLine.Vertex(iVertex + 1)) <= k Then
'        vBissectrisa = CreateBissectrisaVector(mLine, iVertex)
'        If Vector3dDotProductXY(vBissectrisa, vPiket) >= 0 Then
'            vPiket = vBissectrisa
'        Else
'            vPiket = Vector3dScale(vBissectrisa, -1)
'        End If
'    End If
    CreatePiketVector = Vector3dScale(vPiket, CDbl(tbD.Text) * 0.5)
End Function
Private Function GetAngleBetweenTwoVerctors(mLine As LineElement, ByVal iVertex As Long) As Double
    Dim v1 As Vector3d
    Dim v2 As Vector3d
    Dim i As Long
    Dim A As Double
    
    On Error Resume Next
    If (iVertex < mLine.VerticesCount) Then
        If iVertex > 1 Then
            iVertex = iVertex + 1
            v1 = Vector3dSubtractPoint3dPoint3d(mLine.Vertex(i + 1), mLine.Vertex(i))
            v2 = Vector3dSubtractPoint3dPoint3d(mLine.Vertex(i - 1), mLine.Vertex(i))
            A = Vector3dAngleBetweenVectors(v2, v1)
            GetAngleBetweenTwoVerctors = (Pi - A) * 2 / Pi
        End If
    Else
        GetAngleBetweenTwoVerctors = 0
    End If
End Function
Private Function CreateBissectrisaVector(mLine As LineElement, ByVal iVertex As Long) As Vector3d
    Dim v1 As Vector3d
    Dim v2 As Vector3d
    Dim v3 As Vector3d
    On Error Resume Next
    If (iVertex < mLine.VerticesCount) Then
        If iVertex > 1 Then
            iVertex = iVertex + 1
            v1 = Vector3dSubtractPoint3dPoint3d(mLine.Vertex(iVertex + 1), mLine.Vertex(iVertex))
            v2 = Vector3dSubtractPoint3dPoint3d(mLine.Vertex(iVertex - 1), mLine.Vertex(iVertex))
            v3 = Vector3dAdd(Vector3dScale(v1, 1 / Vector3dMagnitude(v1)), Vector3dScale(v2, 1 / Vector3dMagnitude(v2)))
            v3 = Vector3dScale(v3, 1 / Vector3dMagnitude(v3))
            
            CreateBissectrisaVector = v3
        End If
    End If
End Function
Private Sub DrawBoxes(CutLine() As Element)
    Dim i As Long
    Dim j As Long
    Dim t As Long
    Dim VertexOfBosx() As Point3d
    Dim mBox As ShapeElement
    Dim IntersectPoint() As Point3d
    
    For i = 0 To UBound(CutLine) - 1
            ReDim Preserve VertexOfBosx(3)
            VertexOfBosx(2) = CutLine(i + 1).AsLineElement.endPoint
            VertexOfBosx(3) = CutLine(i + 1).AsLineElement.StartPoint
        If i < 4 Then
            t = 0
        Else
            t = 3
        End If
        If i = 0 Then
            VertexOfBosx(0) = CutLine(i).AsLineElement.StartPoint
            VertexOfBosx(1) = CutLine(i).AsLineElement.endPoint
        Else
            For j = i To i - t Step -1
                IntersectPoint = CutLine(i + 1).AsLineElement.GetIntersectionPoints(CutLine(j).AsLineElement, Matrix3dIdentity)
                If UBound(IntersectPoint) >= 0 Then
                    Dim InterPoint As LineElement
                    Set InterPoint = CreateLineElement2(Nothing, IntersectPoint(0), IntersectPoint(0))
                    InterPoint.LineWeight = 8
                    InterPoint.Color = 3
                    ActiveModelReference.AddElement InterPoint
                    InterPoint.Redraw
                    
                    If Point3dDistance(CutLine(i).AsLineElement.StartPoint, IntersectPoint(0)) > Point3dDistance(CutLine(i).AsLineElement.endPoint, IntersectPoint(0)) Then
                        VertexOfBosx(0) = CutLine(i).AsLineElement.StartPoint
                        VertexOfBosx(1) = IntersectPoint(0)
                        VertexOfBosx(2) = CutLine(i + 1).AsLineElement.StartPoint
                        ReDim Preserve VertexOfBosx(2)
                        Set CutLine(i + 1) = CreateLineElement2(Nothing, CutLine(i + 1).AsLineElement.StartPoint, IntersectPoint(0))
                        Set CutLine(i) = CreateLineElement2(Nothing, CutLine(i).AsLineElement.StartPoint, IntersectPoint(0))
                    Else
                        VertexOfBosx(0) = IntersectPoint(0)
                        VertexOfBosx(1) = CutLine(i).AsLineElement.endPoint
                        VertexOfBosx(2) = CutLine(i + 1).AsLineElement.endPoint
                        Set CutLine(i + 1) = CreateLineElement2(Nothing, IntersectPoint(0), CutLine(i + 1).AsLineElement.endPoint)
                        Set CutLine(i) = CreateLineElement2(Nothing, IntersectPoint(0), CutLine(i).AsLineElement.endPoint)
                        ReDim Preserve VertexOfBosx(2)
                    End If
                    Exit For
                Else
                    VertexOfBosx(0) = CutLine(i).AsLineElement.StartPoint
                    VertexOfBosx(1) = CutLine(i).AsLineElement.endPoint
                End If
            Next j
            
        End If
        Set mBox = CreateShapeElement1(Nothing, VertexOfBosx, msdFillModeNotFilled)
        ActiveModelReference.AddElement mBox
        mBox.Redraw
    Next i
    
End Sub
Private Sub RedimPreserve(ByRef mB() As Element)
    Dim i As Long
    On Error Resume Next
    i = UBound(mB) + 1
    If Err.Number = 9 Then
        ReDim mB(0)
    Else: ReDim Preserve mB(i)
    End If
    Err.Clear
End Sub
Function ReversLine(line As LineElement) As LineElement
    Dim countV As Long 'Количество вертексов линии
    Dim Rline As LineElement
    Dim i As Long
    Dim pt() As Point3d
    
    countV = line.VerticesCount
    ReDim Preserve pt(countV - 1)
    For i = 0 To (countV - 1)
        pt(i) = line.Vertex(countV - i)
    Next i
    Set Rline = CreateLineElement1(Nothing, pt())
    Set ReversLine = Rline
End Function

Private Sub cell_Initialize()
    Dim MyCellEnum As CellInformationEnumerator
    Dim MyCell As CellInformation
    ComboBox_cell.Clear
        If IsCellLibraryAttached Then
            Set MyCellEnum = Application.GetCellInformationEnumerator(True, False)
            While MyCellEnum.MoveNext
                Set MyCell = MyCellEnum.Current
                If Not MyCell.IsShared Then ComboBox_cell.AddItem MyCell.Name
                'cmbCell.AddItem MyCell.Name
            Wend
        Else: MsgBox "Библиотека Cell не подключена", vbOKOnly
        End If
End Sub

Private Sub CheckBox_placeCell_Change()
    If CheckBox_placeCell.Value = True Then
        ComboBox_cell.Enabled = True
    ElseIf CheckBox_placeCell.Value = False Then
        ComboBox_cell.Enabled = False
    End If
End Sub


Private Sub CheckBox_textPiket_Click()

End Sub

Private Sub ComboBox_cell_DblClick(ByVal Cancel As MSForms.ReturnBoolean)
    cell_Initialize
End Sub



Private Sub ComboBox_Levels_DblClick(ByVal Cancel As MSForms.ReturnBoolean)
    InitializeLevels ComboBox_Levels
End Sub

Private Sub ComboBoxLeveOfPiketaz_DblClick(ByVal Cancel As MSForms.ReturnBoolean)
    InitializeLevels ComboBoxLeveOfPiketaz
End Sub


Private Sub ComboBoxLeveOfPiket_DblClick(ByVal Cancel As MSForms.ReturnBoolean)
    InitializeLevels ComboBoxLeveOfPiket
End Sub

Private Sub CommandButton_DrawProfil_Click()
    CommandState.StartPrimitive New PCE_DrawCutLine, True
End Sub
Private Sub InitializeFontName(mComboBox As ComboBox)
    Dim MyModel As ModelReference
    Dim myFont As Font
    mComboBox.Clear
    Set MyModel = ActiveDesignFile.DefaultModelReference
        For Each myFont In MyModel.DesignFile.Fonts
            mComboBox.AddItem myFont.Name
        Next
End Sub
Private Sub InitializeJustification(mComboBox As ComboBox)
    mComboBox.AddItem "Right Top"
    mComboBox.AddItem "Right Center"
    mComboBox.AddItem "Right Bottom"
    mComboBox.AddItem "Best Position"
    mComboBox.Value = mComboBox.List(1)
End Sub

Private Sub CommandButton1_Click()
    CommandState.StartLocate New LCE_SetCorridor
End Sub

Private Sub CommandButtonOtmetkiBySelectProfile_Click()
    Dim SelEnum As ElementEnumerator
    Dim mProfile() As Element
    Dim i As Long
    
    Set SelEnum = ActiveModelReference.GetSelectedElements
    mProfile = SelEnum.BuildArrayFromContents
    
    For i = 0 To UBound(mProfile)
        If mProfile(i).IsLineElement Then
            If mProfile(i).Level.Name = MyForm.ComboBoxLevelProfile.Text Then
                DrawProfilePoint mProfile(i), Module1.AngleTxt(mProfile(i).AsLineElement.StartPoint, Point3dAdd(mProfile(i).AsLineElement.StartPoint, Point3dFromVector3d(Vector3dUnitPerpendicularXY(Vector3dFromPoint3d(Point3dSubtract(mProfile(i).AsLineElement.endPoint, mProfile(i).AsLineElement.StartPoint))))))
            End If
        End If
    Next i
    
End Sub

Private Sub UserForm_Initialize()
    InitializeLevels ComboBox_Levels
    InitializeLevels ComboBoxLeveOfPiket
    InitializeLevels ComboBoxLevelProfile
    InitializeLevels ComboBoxLevelOfPiketaz
    
    cell_Initialize
    InitializeFontName ComboBox_Fonts
    InitializeJustification ComboBoxJustification
    RazrydInizialize
    
End Sub

Private Sub RazrydInizialize()
    ComboBox_razryd.AddItem "00"
    ComboBox_razryd.AddItem "000"
    ComboBox_razryd.AddItem "0000"
    ComboBox_razryd.AddItem "00000"
    ComboBox_razryd.AddItem "000000"
    ComboBox_razryd.Value = ComboBox_razryd.List(ComboBox_razryd.ListCount - 1)
End Sub

Attribute VB_Name = "PCE_DrawCutLine"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private stPoint As Point3d
Private endPoint As Point3d
Private bool As Boolean
Private MyLine As LineElement
Implements IPrimitiveCommandEvents

Private Sub IPrimitiveCommandEvents_Cleanup()

End Sub

Private Sub IPrimitiveCommandEvents_DataPoint(Point As Point3d, ByVal View As View)
If bool = False Then
    stPoint = Point
    bool = True
    CommandState.StartDynamics
ElseIf bool = True Then
    endPoint = Point
    CommandState.StopDynamics
    
    bool = False
    DrawProfilePoint MyLine, AngleTxt(stPoint, Point3dAdd(stPoint, Point3dFromVector3d(Vector3dUnitPerpendicularXY(Vector3dFromPoint3d(Point3dSubtract(endPoint, stPoint))))))  '+ Pi * 0.5)
End If

End Sub

Private Sub IPrimitiveCommandEvents_Dynamics(Point As Point3d, ByVal View As View, ByVal DrawMode As MsdDrawingMode)
    Set MyLine = CreateLineElement2(Nothing, stPoint, Point)
    MyLine.Redraw DrawMode
End Sub

Private Sub IPrimitiveCommandEvents_Keyin(ByVal Keyin As String)

End Sub

Private Sub IPrimitiveCommandEvents_Reset()
    CommandState.StartDefaultCommand
End Sub

Private Sub IPrimitiveCommandEvents_Start()
   ' CommandState.EnableAccuSnap
End Sub
