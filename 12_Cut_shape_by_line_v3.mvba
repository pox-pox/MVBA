Attribute VB_Name = "ComplexShapeToShape"
Option Explicit
Function ComplexShapeToShape(CShape As Element) As ShapeElement
    Dim MyEnum As ElementEnumerator
    Dim MyShape As ShapeElement
    Dim Verteces() As Point3d
    Dim i As Integer
    ReDim Verteces(0)
    If CShape.IsComplexShapeElement Then
        Set MyEnum = CShape.AsComplexShapeElement.GetSubElements
            While MyEnum.MoveNext
                For i = 0 To UBound(MyEnum.Current.AsVertexList.GetVertices)
                    Verteces(UBound(Verteces)) = MyEnum.Current.AsLineElement.Vertex(i + 1)
                    ReDim Preserve Verteces(UBound(Verteces) + 1)
                Next i
                ReDim Preserve Verteces(UBound(Verteces) - 1)
            Wend
     '   CShape.IsSnappable = True
        Set MyShape = CreateShapeElement1(CShape, Verteces, msdFillModeNotFilled)
        MyShape.IsSnappable = True
        Set ComplexShapeToShape = MyShape
    ElseIf CShape.IsShapeElement Then
        Set ComplexShapeToShape = CShape.AsShapeElement
    End If
End Function

Attribute VB_Name = "LCE_CompleShapeToShape"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements ILocateCommandEvents

Private Sub ILocateCommandEvents_Accept(ByVal Element As Element, Point As Point3d, ByVal View As View)
    Dim MyShape As ShapeElement
    Set MyShape = ComplexShapeToShape.ComplexShapeToShape(Element)
    ActiveModelReference.RemoveElement Element
    Element.Redraw
    ActiveModelReference.AddElement MyShape
    MyShape.Redraw
    ActiveDesignFile.Views(View.Index).Redraw
End Sub

Private Sub ILocateCommandEvents_Cleanup()

End Sub

Private Sub ILocateCommandEvents_Dynamics(Point As Point3d, ByVal View As View, ByVal DrawMode As MsdDrawingMode)
    CommandState.StartLocate Me
End Sub

Private Sub ILocateCommandEvents_LocateFailed()

End Sub

Private Sub ILocateCommandEvents_LocateFilter(ByVal Element As Element, Point As Point3d, Accepted As Boolean)
Accepted = False
    If Element.IsComplexShapeElement Then
        ShowCommand "ComplexShape to Shape"
        ShowPrompt "Подтвердите выделение ЛКМ"
        Accepted = True
    End If
End Sub

Private Sub ILocateCommandEvents_LocateReset()
    CommandState.StartDefaultCommand
End Sub

Private Sub ILocateCommandEvents_Start()
    ShowCommand "ComplexShape to Shape"
    ShowPrompt "Выделите ComplexShape"

End Sub

Attribute VB_Name = "Module"
Option Explicit

Sub Main()
    uf_Cut.show vbModeless
End Sub

Attribute VB_Name = "PCE_DrawCutLine"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private stPoint As Point3d
Private endPoint As Point3d
Private bool As Boolean
Private MyLine As LineElement
Implements IPrimitiveCommandEvents

Private Sub IPrimitiveCommandEvents_Cleanup()

End Sub

Private Sub IPrimitiveCommandEvents_DataPoint(Point As Point3d, ByVal View As View)
If bool = False Then
    stPoint = Point
    bool = True
    CommandState.StartDynamics
ElseIf bool = True Then
    endPoint = Point
    CommandState.StopDynamics
    ScanShape
    bool = False
End If
End Sub

Private Sub IPrimitiveCommandEvents_Dynamics(Point As Point3d, ByVal View As View, ByVal DrawMode As MsdDrawingMode)
    Set MyLine = CreateLineElement2(Nothing, stPoint, Point)
    MyLine.Redraw DrawMode
End Sub

Private Sub IPrimitiveCommandEvents_Keyin(ByVal Keyin As String)

End Sub

Private Sub IPrimitiveCommandEvents_Reset()
    CommandState.StartDefaultCommand
End Sub

Private Sub IPrimitiveCommandEvents_Start()
   ' CommandState.EnableAccuSnap
End Sub

Private Sub ScanShape()
    Dim myFilter As New ElementScanCriteria
    Dim MyEnum As ElementEnumerator
    Dim Shape As ShapeElement
    Dim mElement() As Element
    Dim i As Long
    
    myFilter.ExcludeAllTypes
    myFilter.IncludeType msdElementTypeShape
    myFilter.IncludeType msdElementTypeComplexShape
    
    Set MyEnum = ActiveModelReference.Scan(myFilter)
'        While MyEnum.MoveNext
'            If (MyEnum.Current.Level.IsDisplayedInView(ActiveDesignFile.Views.Item(1)) = True And uf_Cut.CheckBox_visible_elenments.Value = True) Or uf_Cut.CheckBox_visible_elenments.Value = False Then ' Резать только видимые элементы
'     '           Set Shape = ComplexShapeToShape.ComplexShapeToShape(MyEnum.Current)
'                CutShape MyEnum.Current, MyLine
'            End If
'        Wend
'
     mElement = MyEnum.BuildArrayFromContents
    
    For i = 0 To UBound(mElement)
        
        If (mElement(i).Level.IsDisplayedInView(ActiveDesignFile.Views.Item(1)) = True And uf_Cut.CheckBox_visible_elenments.Value = True) Or uf_Cut.CheckBox_visible_elenments.Value = False Then ' Резать только видимые элементы
            'Set Shape = ComplexShapeToShape.ComplexShapeToShape(mElement(i))
            CutShape mElement(i), MyLine
        End If
    Next i
    
End Sub

Private Sub CutShape(IniShape As Element, CutLine As LineElement)
    Dim iPoint() As Point3d ' Точки пересечения
    Dim Seg1 As Long
    Dim Seg2 As Long
    Dim intPoint1 As Point3d
    Dim intPoint2 As Point3d
    Dim Vertex1() As Point3d
    Dim Vertex2() As Point3d
    Dim Shape1 As ShapeElement
    Dim Shape2 As ShapeElement
    Dim tmpShape As ShapeElement
    Dim i As Integer
    Dim j As Integer
    
'    Dim mEnum As ElementEnumerator
'    Dim mElements() As Element
'    ReDim mElements(1)
    
    j = 1
    
    iPoint = IniShape.AsIntersectableElement.GetIntersectionPoints(CutLine, Matrix3dIdentity)
    
        If UBound(iPoint) = 1 Then
            If IniShape.IsShapeElement Or IniShape.IsComplexShapeElement Then
'                Set mElements(0) = CutLine
'                Set mElements(1) = IniShape
'                Set mEnum = GetIntersectionShapesFromRegion(mElements, Nothing, msdFillModeNotFilled)
'
                Set tmpShape = ComplexShapeToShape.ComplexShapeToShape(IniShape)
                  ReDim Vertex1(0)
                  ReDim Vertex2(0)
                  If tmpShape.GetClosestSegment(iPoint(0)) > tmpShape.GetClosestSegment(iPoint(1)) Then
                      Seg1 = tmpShape.GetClosestSegment(iPoint(1))
                      intPoint1 = iPoint(1)
                      Seg2 = tmpShape.GetClosestSegment(iPoint(0))
                      intPoint2 = iPoint(0)
                  ElseIf tmpShape.GetClosestSegment(iPoint(0)) < tmpShape.GetClosestSegment(iPoint(1)) Then
                      Seg1 = tmpShape.GetClosestSegment(iPoint(0)) + 1
                      intPoint1 = iPoint(0)
                      Seg2 = tmpShape.GetClosestSegment(iPoint(1)) + 1
                      intPoint2 = iPoint(1)
                  End If
                      
                  For i = 0 To (Seg1 - 1)
                      Vertex1(i) = tmpShape.Vertex(i + 1)
                      ReDim Preserve Vertex1(UBound(Vertex1) + 1)
                  Next i
                      Vertex1(Seg1) = intPoint1
                      ReDim Preserve Vertex1(UBound(Vertex1) + 1)
                      Vertex1(Seg1 + 1) = intPoint2
                      ReDim Preserve Vertex1(UBound(Vertex1) + 1)
                      
                  For i = (Seg2 + 1) To tmpShape.VerticesCount
                      Vertex1(UBound(Vertex1)) = tmpShape.Vertex(i)
                      ReDim Preserve Vertex1(UBound(Vertex1) + 1)
                  Next i
                      ReDim Preserve Vertex1(UBound(Vertex1) - 1)
                      
        ''''''''''''''''''''''''''''''''''''''''''''''''''''''''''''''''' второй конту
                  Vertex2(0) = intPoint1
                  ReDim Preserve Vertex2(j)
                  For i = (Seg1 + 1) To Seg2
                      Vertex2(j) = tmpShape.Vertex(i)
                      j = j + 1
                      ReDim Preserve Vertex2(j)
                  Next i
                      Vertex2(j) = intPoint2
                  Set Shape1 = CreateShapeElement1(tmpShape, Vertex1(), msdFillModeNotFilled)
                  ActiveModelReference.AddElement Shape1
                  Shape1.Redraw
                  Set Shape2 = CreateShapeElement1(tmpShape, Vertex2(), msdFillModeNotFilled)
                  ActiveModelReference.AddElement Shape2
                  Shape2.Redraw
                  If uf_Cut.CheckBox_SplitText.Value Then SplitBoxName IniShape.AsShapeElement, Shape1, Shape2
                  If uf_Cut.CheckBox_Delete_iniShape.Value = True Then ' Удалять исходныуй контур
                    If IniShape.IsComplexShapeElement Then
                        ActiveModelReference.RemoveElement IniShape
                        IniShape.Redraw
                    ElseIf IniShape.IsShapeElement Then
                        ActiveModelReference.RemoveElement tmpShape
                        tmpShape.Redraw
                    End If
                  End If
            End If
        End If
    Erase iPoint
End Sub

Private Sub SplitBoxName(IniBox As ShapeElement, FirstBox As ShapeElement, SecondBox As ShapeElement)

    Dim mFilter As New ElementScanCriteria
    Dim mEnum As ElementEnumerator
    Dim FirstText As TextElement
    Dim SecondText As TextElement
    Dim mText() As Element
    Dim i As Long
    
    mFilter.ExcludeAllLevels
    mFilter.ExcludeAllTypes
    
    mFilter.IncludeLevel IniBox.Level
    mFilter.IncludeType msdElementTypeText
    
    Set mEnum = ActiveModelReference.Scan(mFilter)
    mText = mEnum.BuildArrayFromContents
    
    Dim IniText As String
    
   ' While mEnum.MoveNext
    For i = 0 To UBound(mText)
        If Point3dInPolygonXY(mText(i).AsTextElement.Origin, IniBox.GetVertices) = 1 Then
            IniText = mText(i).AsTextElement.Text
            ActiveSettings.TextStyle.Height = mText(i).AsTextElement.TextStyle.Height * 0.5
            ActiveSettings.TextStyle.Width = mText(i).AsTextElement.TextStyle.Width * 0.5
            ActiveSettings.TextStyle.Font = mText(i).AsTextElement.TextStyle.Font
            ActiveSettings.TextStyle.Justification = mText(i).AsTextElement.TextStyle.Justification
            
            Set FirstText = CreateTextElement1(Nothing, IniText, FirstBox.Centroid, Matrix3dIdentity)
            Set SecondText = CreateTextElement1(Nothing, IncrLastCharInString(IniText), SecondBox.Centroid, Matrix3dIdentity)
            FirstText.Level = mText(i).AsTextElement.Level
            SecondText.Level = mText(i).AsTextElement.Level
            ActiveModelReference.RemoveElement mText(i)
            ActiveModelReference.AddElement FirstText
            ActiveModelReference.AddElement SecondText
            RedrawAllViews
        End If
    Next i
 '   Wend
    

End Sub
Function IncrLastCharInString(mString As String) As String
    Dim LastChar As String
    
    LastChar = Right(mString, 1)
    If Asc(LastChar) < 64 Then
        IncrLastCharInString = mString & "a"
    ElseIf Asc(LastChar) > 64 Then
        IncrLastCharInString = Left(mString, Len(mString) - 1) & Char_incr(Right(mString, 1))
    End If
    
    
End Function
Function Char_incr(iString As String) As String
    Dim a() As Byte, b(), i As Long
    a() = StrConv(iString, vbFromUnicode)
    ReDim Preserve b(0 To UBound(a))
    On Error Resume Next
    For i = 0 To UBound(a)
        b(i) = Chr(a(i) + 1)
    Next
    Char_incr = Join(b, "")
End Function

Attribute VB_Name = "uf_Cut"
Attribute VB_Base = "0{A5F5D5BB-17D1-43DA-9519-9BA57C5B8BF7}{1FDD516E-260C-4E42-942F-6927D1A00388}"
Attribute VB_GlobalNameSpace = False
Attribute VB_Creatable = False
Attribute VB_PredeclaredId = True
Attribute VB_Exposed = False
Attribute VB_TemplateDerived = False
Attribute VB_Customizable = False
Option Explicit

Private Sub button_cut_Click()
    CommandState.StartPrimitive New PCE_DrawCutLine, True
End Sub

Private Sub CommandButton_complexShapeToShape_Click()
    CommandState.StartLocate New LCE_CompleShapeToShape
End Sub
