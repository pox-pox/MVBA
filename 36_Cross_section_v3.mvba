Attribute VB_Name = "Module1"
Option Explicit
Public basPoint As Point3d

Sub Main()
    MyForm.Show vbModeless
    basPoint.X = 2115600
    basPoint.Y = 170100
End Sub

Attribute VB_Name = "MyForm"
Attribute VB_Base = "0{2352A393-9164-4BE1-897E-5AA66E7F7F61}{A8C0B208-0D31-41EA-8EEE-28E175E48787}"
Attribute VB_GlobalNameSpace = False
Attribute VB_Creatable = False
Attribute VB_PredeclaredId = True
Attribute VB_Exposed = False
Attribute VB_TemplateDerived = False
Attribute VB_Customizable = False
Option Explicit

Private Sub IniLevels()
    Dim myLevel As Level
        MyForm.ComboBox_Levels.Clear
            For Each myLevel In ActiveDesignFile.Levels
                MyForm.ComboBox_Levels.AddItem myLevel.Name
            Next
End Sub
Private Sub btnCreate_Click()
Dim Piket() As Point3d
Dim MyLineVert() As Point3d ' Вертексы линии
Dim i As Double
Dim k As Double
Dim v As Double ' Количество вертексов в искомой линии
Dim j As Double 'Количество пикетов
Dim Point As LineElement
Dim pik As Double   'Расстояние между пикетами
Dim lineEnum As ElementEnumerator
Dim mFilter As New ElementScanCriteria
Dim MyLine As LineElement
Dim vLine As Vector3d   ' Вектор отрезка
Dim vPiket As Vector3d  ' Вектор пикета
Dim Ax As Double
Dim Ay As Double
Dim Az As Double
Dim p1 As Point3d   'Начальная точка пикета
Dim p2 As Point3d   'Конечная точка пикета
Dim L As Double   'Накопленная длинна пикетов
Dim S As Double   'НАкопленная длина отрезков линии
Dim D As Double   'Длина отрезка
Dim MyTxt As TextElement    'Подпись пикета
Dim RotationMatrix As Matrix3d
Dim rOtmetki As Double



pik = CDbl(tbPik.Text)
D = CDbl(tbD.Text)

    mFilter.ExcludeAllTypes
    mFilter.ExcludeAllLevels
    
    mFilter.IncludeLevel ActiveDesignFile.Levels(MyForm.ComboBox_Levels.Text)
    mFilter.IncludeType msdElementTypeLineString
    mFilter.IncludeType msdElementTypeComplexString

Set lineEnum = ActiveModelReference.Scan(mFilter)


    While lineEnum.MoveNext
        Select Case lineEnum.Current.Type
            Case msdElementTypeLineString
            ReDim Piket(0)
            j = 0
                Set MyLine = lineEnum.Current
                If cbxRevers.Value = True Then Set MyLine = ReversLine(MyLine)
                j = MyLine.Length \ pik
                    If j > 0 Then
                            Piket(0) = MyLine.StartPoint
                            On Error Resume Next
                        For i = 1 To j
                            ReDim Preserve Piket(UBound(Piket) + 1)
                            Piket(i) = MyLine.PointAtDistance(pik * (i))
                            
                        Next i
'                        For i = UBound(Piket) To 1 Step -1
'                            Piket(i) = Piket(i - 1)
'                        Next i
'                            Piket(i) = MyLine.StartPoint
                            'ReDim Preserve Piket(UBound(Piket) - 1)
                    End If
                For k = 0 To UBound(Piket)
                i = MyLine.GetClosestSegment(Piket(k))
                
                    
                    On Error Resume Next

                    Ax = MyLine.Vertex(i + 2).X - Piket(k).X
                    Ay = MyLine.Vertex(i + 2).Y - Piket(k).Y
                    If Ax = 0 And Ay = 0 Then
                    Ax = MyLine.Vertex(i + 3).X - Piket(k).X
                    Ay = MyLine.Vertex(i + 3).Y - Piket(k).Y
                    End If
                    vLine = Vector3dFromXY(Ax, Ay)
                    vPiket = Vector3dUnitPerpendicularXY(vLine)
                    vPiket = Vector3dScale(vPiket, D * 0.5)
                    p1.X = Vector3dGetComponent(vPiket, 0) + Piket(k).X
                    p1.Y = Vector3dGetComponent(vPiket, 1) + Piket(k).Y
                    vPiket = Vector3dScale(vPiket, -1)
                    p2.X = Vector3dGetComponent(vPiket, 0) + Piket(k).X
                    p2.Y = Vector3dGetComponent(vPiket, 1) + Piket(k).Y
                    
                    Set Point = CreateLineElement2(Nothing, p1, p2)
                        If CheckBox_piket.Value = True Then ' Ставить пикетаж
                            ActiveModelReference.AddElement Point
                            Point.Redraw
                        End If
                        
                    If cbxReturn.Value = True Then
                        rOtmetki = AngleTxt(MyLine.Vertex(i + 1), MyLine.Vertex(i + 2)) + Pi
                        RotationMatrix = Matrix3dFromAxisAndRotationAngle(2, rOtmetki)
                        Set MyTxt = CreateTextElement1(Nothing, CStr(k), p2, RotationMatrix)
                    Else
                        rOtmetki = AngleTxt(MyLine.Vertex(i + 1), MyLine.Vertex(i + 2))
                        RotationMatrix = Matrix3dFromAxisAndRotationAngle(2, rOtmetki)
                        Set MyTxt = CreateTextElement1(Nothing, CStr(k), p1, RotationMatrix)
                    End If
                        
                            DrawProfilePoint Point, rOtmetki, CStr(k)
                        If CheckBox_textPiket.Value = True Then ' Подписи пикетов
                            MyTxt.TextStyle.Justification = msdTextJustificationCenterBottom
                            ActiveModelReference.AddElement MyTxt
                            MyTxt.Redraw
                        End If
                    
                Next k
        End Select
    Wend
End Sub
Private Sub DrawProfilePoint(mProfile As LineElement, mRot As Double, tSect As String)
    Dim MyEnum As ElementEnumerator
    Dim mStructLine() As Element
    Dim i As Long ' Счетчик структурных линий
    Dim j As Long ' Счетчик пересечений
    Dim mPoint As LineElement ' Точка пересечения
    Dim pPoint() As Point3d
    Dim LevelName() As String
    Dim mDist() As Double
    Dim arrPoints() As Point3d
    Dim sect As String
    
    Dim mCell As CellElement
    Dim tLevel As TextElement
    
    sect = tSect
    Set MyEnum = ActiveModelReference.GetSelectedElements
    mStructLine = MyEnum.BuildArrayFromContents
  '  If UBound(mStructLine) < 0 Then MsgBox "Регионы не выделены"
            ReDim LevelName(0)
            ReDim mDist(0)
            ReDim arrPoints(0)
    For i = 0 To UBound(mStructLine)
        pPoint = mStructLine(i).AsIntersectableElement.GetIntersectionPoints(mProfile, Matrix3dIdentity)
            If UBound(pPoint) <> -1 Then
            
                For j = 0 To UBound(pPoint)
                    If CheckBox_placeCell.Value = True And ComboBox_cell.Text <> "" Then
                        Set mCell = CreateCellElement3(ComboBox_cell.Text, pPoint(j), True)
                        ActiveModelReference.AddElement mCell
                        mCell.Redraw
                    Else
                        Set mPoint = CreateLineElement2(Nothing, pPoint(j), pPoint(j))
                        mPoint.LineWeight = 5
                        ActiveModelReference.AddElement mPoint
                        mPoint.Redraw
                    End If
                    LevelName(UBound(LevelName)) = mStructLine(i).Level.Name
                    mDist(UBound(mDist)) = Point3dDistanceXY(mProfile.AsLineElement.StartPoint, pPoint(j))
                    arrPoints(UBound(arrPoints)) = pPoint(j)
                    
                    DrawTxt pPoint(j), mRot, mStructLine(i).Level.Name, mDist(UBound(mDist))
                    ReDim Preserve LevelName(UBound(LevelName) + 1)
                    ReDim Preserve mDist(UBound(mDist) + 1)
                    ReDim Preserve arrPoints(UBound(arrPoints) + 1)
                Next j
'                ReDim Preserve LevelName(UBound(LevelName) - 1)
'                ReDim Preserve mDist(UBound(mDist) - 1)
            End If
    Next i
    
    ReDim Preserve LevelName(UBound(LevelName) - 1)
    ReDim Preserve mDist(UBound(mDist) - 1)
    ReDim Preserve arrPoints(UBound(arrPoints) - 1)
    basPoint.Y = basPoint.Y + 30 ' -----------------------------Расстояние между профилями
    DrawShtamp basPoint, arrPoints, mDist, LevelName, sect
    
End Sub
Private Sub DrawTxt(oPoint As Point3d, mRotation As Double, tLevel As String, dist As Double)
    Dim mText As TextElement
    Dim tTransform As Transform3d
    Dim tPoint As Point3d
    
    tPoint.X = oPoint.X + CDbl(TextBox_offsetX.Text)
    tPoint.Y = oPoint.Y + CDbl(TextBox_offsetY.Text)
    tPoint.Z = oPoint.Z
    
    Set mText = CreateTextElement1(Nothing, tLevel & " (H=" & FormatNumber(Round(CStr(oPoint.Z), 3), 3, vbTrue, vbTrue, vbTrue) & "; " & "Cum.Dist.=" & FormatNumber(Round(CStr(dist), 3), 3, vbTrue, vbTrue, vbTrue) & ")", tPoint, Matrix3dIdentity)
    mText.RotateAboutZ oPoint, mRotation
    ActiveModelReference.AddElement mText
    mText.Redraw
    
'    tPoint.Y = tPoint.Y - 1
'
'    Set mText = CreateTextElement1(Nothing, tLevel, tPoint, Matrix3dIdentity)
'    mText.TextStyle.Height = 0.25
'    mText.TextStyle.Width = 0.25
'
'    mText.RotateAboutZ oPoint, mRotation
'    ActiveModelReference.AddElement mText
'    mText.Redraw
'
    
End Sub
Private Sub DrawShtamp(bPoint As Point3d, aPoint() As Point3d, aDist() As Double, tLevel() As String, sect As String)

Dim withFirstCol As Double
Dim i As Integer
Dim stPt As Point3d
Dim edPt As Point3d
Dim Line As LineElement
Dim colH As Double
Dim minHeight As Double
Dim RefHeight As Double
Dim DeltaRefHeight As Double
Dim DeltaH As Double ' Отступ по горизонтали вот первой колонки
Dim ArAnno
Dim anno As TextElement
Dim profPoint() As Point3d
Dim tmpPoint As Point3d
Dim m As Integer
Dim n As Integer
Dim profPoly As LineElement
Dim vertLine As LineElement
Dim oP As Point3d
Dim RotationMatrix As Matrix3d
Dim AnnoHeight As Double
Dim tmpDist As Double ' рассчетная дистанция

ReDim profPoint(0)

ArAnno = Array("Information", "Cum.Distance", "Distance", "Height")
DeltaH = 2                  ' Отступ профиля с двух сторон
withFirstCol = 18           ' Ширина первой колонки
colH = 3                    ' Высота строк
DeltaRefHeight = 2          ' Отступ по высоте от таблицы до профиля
AnnoHeight = colH * 0.07    ' Высота названия слоев в профиле
stPt = bPoint

edPt.X = bPoint.X + withFirstCol + CDbl(tbD.Text) + 2 * DeltaH
edPt.Y = bPoint.Y
RotationMatrix = Matrix3dFromAxisAndRotationAngle(2, Pi / 2)


For i = 0 To UBound(aDist)
    Debug.Print aDist(i)
Next i

    ' ------------------------Горизонтальные полосы
    For i = 0 To 4
        Set Line = CreateLineElement2(Nothing, stPt, edPt)
        ActiveModelReference.AddElement Line
        Line.Redraw
        stPt.Y = stPt.Y + colH
        edPt.Y = edPt.Y + colH
    Next i
        edPt.Y = bPoint.Y + colH * 4
        edPt.X = bPoint.X
        stPt.X = bPoint.X
        stPt.Y = bPoint.Y
    ' ------------------------Вертикальные полосы--------------------------
    For i = 0 To 2
        Select Case i
            Case 1
                stPt.X = stPt.X + withFirstCol
                edPt.X = edPt.X + withFirstCol
            Case 2
                stPt.X = stPt.X + CDbl(tbD.Text) + 2 * DeltaH
                edPt.X = edPt.X + CDbl(tbD.Text) + 2 * DeltaH
        End Select
    Set Line = CreateLineElement2(Nothing, stPt, edPt)
    ActiveModelReference.AddElement Line
    Line.Redraw
    Next i

     ' ------------------------Заголовки строк ----------------------------------
    stPt.Y = bPoint.Y + colH * 0.2
    stPt.X = bPoint.X + colH * 0.3
    For i = 0 To 3
        Set anno = CreateTextElement1(Nothing, ArAnno(i), stPt, Matrix3dIdentity)
        anno.TextStyle.Height = colH * 0.4
        anno.TextStyle.Width = colH * 0.4
        ActiveModelReference.AddElement anno
        anno.Redraw
        stPt.Y = stPt.Y + colH
    Next i
    
    '--------------------------- Вычисление минимальной высоты в профиле (Refrence height)(Scale)--------
    minHeight = aPoint(0).Z
        If UBound(aPoint) > 0 Then
            For i = 1 To UBound(aPoint)
                If aPoint(i).Z < minHeight Then
                    minHeight = aPoint(i).Z
                End If
            Next i
        End If
     RefHeight = minHeight - DeltaRefHeight
     
     stPt.Y = basPoint.Y + 4.2 * colH
     stPt.X = bPoint.X + colH * 0.3
     Set anno = CreateTextElement1(Nothing, "Reference height: " & FormatNumber(Round(CStr(RefHeight), 3), 3, vbTrue, vbTrue, vbTrue) & " ft", stPt, Matrix3dIdentity)
       anno.TextStyle.Height = colH * 0.1
       anno.TextStyle.Width = colH * 0.1
       ActiveModelReference.AddElement anno
       anno.Redraw
    stPt.Y = basPoint.Y + 4.5 * colH
    Set anno = CreateTextElement1(Nothing, "Scale: 1/1", stPt, Matrix3dIdentity)
    anno.TextStyle.Height = colH * 0.1
    anno.TextStyle.Width = colH * 0.1
    ActiveModelReference.AddElement anno
    anno.Redraw
       
    '------------------------------ Вертикальные отвесы с профиля
     For i = 0 To UBound(aPoint)
        profPoint(i).X = withFirstCol + basPoint.X + DeltaH + aDist(i)
        profPoint(i).Y = basPoint.Y + 4 * colH + DeltaRefHeight + aPoint(i).Z - RefHeight
        Set profPoly = CreateLineElement2(Nothing, profPoint(i), profPoint(i))
        ActiveModelReference.AddElement profPoly
        profPoly.Color = 2
        profPoly.Rewrite
        
        profPoly.Redraw
        ReDim Preserve profPoint(UBound(profPoint) + 1)
    Next i
    
        ReDim Preserve profPoint(UBound(profPoint) - 1)
'        Set profPoly = CreateLineElement1(Nothing, profPoint)
'        ActiveModelReference.AddElement profPoly
'        profPoly.Color = 2
'        profPoly.Redraw
    
    For i = 0 To UBound(profPoint)
        oP.X = profPoint(i).X
        oP.Y = basPoint.Y + colH
        Set vertLine = CreateLineElement2(Nothing, profPoint(i), oP)
        ActiveModelReference.AddElement vertLine
        vertLine.Redraw
        
        '----Cum distance
        
        DrawAnno profPoint(i).X, bPoint.Y + colH * 1.2, aDist(i), colH, RotationMatrix
        '---- Height
        DrawAnno profPoint(i).X, bPoint.Y + colH * 3.2, aPoint(i).Z, colH, RotationMatrix
        '----- Information
        stPt.X = profPoint(i).X
        stPt.Y = bPoint.Y + colH * 0.1
        Set anno = CreateTextElement1(Nothing, tLevel(i), stPt, RotationMatrix)
        anno.TextStyle.Height = AnnoHeight
        anno.TextStyle.Width = AnnoHeight
        ActiveModelReference.AddElement anno
        anno.Redraw
    Next i
    
        '------ Отображение буфера на профиле
        
        stPt.X = basPoint.X + withFirstCol + DeltaH
        stPt.Y = basPoint.Y + colH
        edPt.X = stPt.X
        edPt.Y = basPoint.Y + colH * 4
        Set Line = CreateLineElement2(Nothing, stPt, edPt)
        ActiveModelReference.AddElement Line
        Line.Redraw
        DrawAnno stPt.X, bPoint.Y + colH * 1.2, 0, colH, RotationMatrix
        stPt.Y = bPoint.Y + colH * 0.1
        Set anno = CreateTextElement1(Nothing, "Buffer: -" & CDbl(tbD.Text) * 0.5 & "ft", stPt, RotationMatrix)
        anno.TextStyle.Height = AnnoHeight
        anno.TextStyle.Width = AnnoHeight
        ActiveModelReference.AddElement anno
        anno.Redraw
        
        
        stPt.X = basPoint.X + withFirstCol + DeltaH + CDbl(tbD.Text)
        stPt.Y = basPoint.Y + colH
        edPt.X = stPt.X
        edPt.Y = basPoint.Y + colH * 4
        Set Line = CreateLineElement2(Nothing, stPt, edPt)
        ActiveModelReference.AddElement Line
        Line.Redraw
        DrawAnno stPt.X, bPoint.Y + colH * 1.2, CDbl(tbD.Text), colH, RotationMatrix
        stPt.Y = bPoint.Y + colH * 0.1
        Set anno = CreateTextElement1(Nothing, "Buffer: +" & CDbl(tbD.Text) * 0.5 & "ft", stPt, RotationMatrix)
        anno.TextStyle.Height = AnnoHeight
        anno.TextStyle.Width = AnnoHeight
        ActiveModelReference.AddElement anno
        anno.Redraw
    
    '------------Сортировака точек
        For n = 0 To UBound(profPoint)
            For m = 0 To UBound(profPoint)
                If m <> n Then
                    If profPoint(m).X > profPoint(n).X Then
                        tmpPoint = profPoint(n)
                        profPoint(n) = profPoint(m)
                        profPoint(m) = tmpPoint
                    End If
                End If
            Next m
        Next n
    
        Set profPoly = CreateLineElement1(Nothing, profPoint)
        ActiveModelReference.AddElement profPoly
        profPoly.Color = 2
        profPoly.Rewrite
        profPoly.Redraw
        
        
    '------------- Distance
    ActiveSettings.TextStyle.Justification = msdTextJustificationCenterBottom
    
    For i = 0 To UBound(profPoint) + 1
        If i = 0 Then
            tmpDist = -(profPoint(i).X - basPoint.X - withFirstCol - DeltaH)
        ElseIf i = UBound(profPoint) + 1 Then
            tmpDist = basPoint.X + CDbl(tbD.Text) + withFirstCol + DeltaH - profPoint(i - 1).X
        Else
            tmpDist = -profPoint(i).X + profPoint(i - 1).X
        End If
    If i = UBound(profPoint) + 1 Then
        DrawAnno profPoint(i - 1).X + tmpDist * 0.5, bPoint.Y + colH * 2.2, tmpDist, colH, Matrix3dIdentity
    Else
        DrawAnno profPoint(i).X + tmpDist * 0.5, bPoint.Y + colH * 2.2, tmpDist, colH, Matrix3dIdentity
    End If
    Next i
    ActiveSettings.TextStyle.Justification = msdTextJustificationLeftBottom
    '--------------- Section
    
    stPt.Y = basPoint.Y - colH * 0.2
     stPt.X = bPoint.X + colH * 0.3
     Set anno = CreateTextElement1(Nothing, "Section " & sect, stPt, Matrix3dIdentity)
       anno.TextStyle.Height = colH * 0.1
       anno.TextStyle.Width = colH * 0.1
       ActiveModelReference.AddElement anno
       anno.Redraw

End Sub

Private Sub DrawAnno(bX As Double, bY As Double, txt As Double, colH As Double, rot As Matrix3d)
    Dim anno As TextElement
    Dim bPoint As Point3d
    Dim RotationMatrix As Matrix3d
    RotationMatrix = Matrix3dFromAxisAndRotationAngle(2, Pi / 2)
    
    bPoint.X = bX
    bPoint.Y = bY
    Set anno = CreateTextElement1(Nothing, FormatNumber(Round(CStr(Abs(txt)), 3), 3, vbTrue, vbTrue, vbTrue), bPoint, rot)
        anno.TextStyle.Height = colH * 0.1
        anno.TextStyle.Width = colH * 0.1
        ActiveModelReference.AddElement anno
        anno.Redraw
End Sub


Function AngleTxt(pSt As Point3d, pEnd As Point3d) As Double
Dim dAng As Double
Dim Angle As Double
Dim ang As Double
Dim dx As Double
Dim dy As Double
dx = pEnd.X - pSt.X
dy = pEnd.Y - pSt.Y
If dy <> 0 Then
    ang = Atn(dx / dy)
    If dx >= 0 And dy > 0 Then
        dAng = ang
    ElseIf dx >= 0 And dy < 0 Then
        dAng = ang + Pi
    ElseIf dx < 0 And dy < 0 Then
        dAng = ang + Pi
    ElseIf dx < 0 And dy > 0 Then
        dAng = ang + 2 * Pi
    End If
ElseIf dy = 0 Then

    If dx > 0 Then
        dAng = Pi / 2
    ElseIf dx < 0 Then
        dAng = 3 * Pi / 4
    End If
End If
Angle = Pi / 2 - dAng

If Angle > Pi * 0.5 And Angle < Pi * 1.5 Then Angle = Angle + Pi
If Angle > -Pi * 1.5 And Angle < -Pi * 0.5 Then Angle = Angle + Pi

AngleTxt = Angle
End Function
Function ReversLine(Line As LineElement) As LineElement
Dim countV As Long 'Количество вертексов линии
Dim Rline As LineElement
Dim i As Long
Dim pt() As Point3d
countV = Line.VerticesCount
ReDim Preserve pt(countV - 1)
For i = 0 To (countV - 1)
    pt(i) = Line.Vertex(countV - i)
Next i
Set Rline = CreateLineElement1(Nothing, pt())
Set ReversLine = Rline
End Function

Private Sub cell_Initialize()
    Dim MyCellEnum As CellInformationEnumerator
    Dim MyCell As CellInformation
    ComboBox_cell.Clear
        If IsCellLibraryAttached Then
            Set MyCellEnum = Application.GetCellInformationEnumerator(True, False)
            While MyCellEnum.MoveNext
                Set MyCell = MyCellEnum.Current
                If Not MyCell.IsShared Then ComboBox_cell.AddItem MyCell.Name
                'cmbCell.AddItem MyCell.Name
            Wend
        Else: MsgBox "Библиотека Cell не подключена", vbOKOnly
        End If
End Sub

Private Sub CheckBox_placeCell_Change()
    If CheckBox_placeCell.Value = True Then
        ComboBox_cell.Enabled = True
    ElseIf CheckBox_placeCell.Value = False Then
        ComboBox_cell.Enabled = False
    End If
End Sub

Private Sub CheckBox_placeCell_Click()

End Sub

Private Sub ComboBox_cell_DblClick(ByVal Cancel As MSForms.ReturnBoolean)
    cell_Initialize
End Sub

Private Sub UserForm_Initialize()
    IniLevels
    cell_Initialize
End Sub
