Attribute VB_Name = "LCE_HP_by_border"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private SelElement As Element

Implements ILocateCommandEvents
Private Sub ILocateCommandEvents_Accept(ByVal Element As Element, point As Point3d, ByVal View As View)
    Dim MyLine As LineElement ' Линия обозначающая бордюр
    Dim tp As Point3d ' Верхняя точка бордюра
    Dim bP As Point3d ' Нижняя точка борюра
    Dim tpT As Point3d ' точка вставки верхнего текста
    Dim bpT As Point3d ' точка вставки нижнего текста
    Dim tText As TextElement ' Верхняя подпись
    Dim bText As TextElement ' Нижняя подпись
    
    Dim Cherta As LineElement ' Дробная черта
    Dim stP As Point3d ' Начальная точка черты
    Dim endP As Point3d ' Конечная точка черты
    Dim LenghC As Double ' Длина черты

    Dim hpCell As CellElement ' Cell отметки высоты
    Dim HeightT As Double ' Активная высота текста
    Dim lowTT As Point3d ' Границы контэйнера верхнего текста
    Dim highTT As Point3d
    Dim lowBT As Point3d ' Границы контэнера нижнего текста
    Dim highBT As Point3d
    
     If MyForm.cbPoint.Value = True Then
        bP = BottomPoint
        tp = TopPoint
    End If
    
    Set MyLine = SelElement
    If MyLine.StartPoint.Z < MyLine.EndPoint.Z Then
        bP = MyLine.StartPoint
        tp = MyLine.EndPoint
    ElseIf MyLine.StartPoint.Z > MyLine.EndPoint.Z Then
        bP = MyLine.EndPoint
        tp = MyLine.StartPoint
    End If
    
    
    HeightT = ActiveSettings.TextStyle.Height
    ' вычисление точек вставки верхнего и нижнего текстов
    tpT.Y = point.Y + 0.1
    bpT.Y = point.Y - 0.1 - HeightT
    
    tpT.X = point.X '+ CDbl(MyForm.tbDist.Text)
    bpT.X = point.X '+ CDbl(MyForm.tbDist.Text)
    
    tpT.Z = bP.Z
    bpT.Z = bP.Z
    
    stP = bP
    stP.X = stP.X ' + CDbl(MyForm.tbDist.Text)
    
    Debug.Print HeightT
    Set bText = CreateTextElement1(Nothing, FormatNumber(Round(bP.Z, 2), 2, vbTrue, vbTrue, vbTrue), bpT, Matrix3dIdentity)
    Set tText = CreateTextElement1(Nothing, FormatNumber(Round(tp.Z, 2), 2, vbTrue, vbTrue, vbTrue), tpT, Matrix3dIdentity)
    lowTT = tText.Range.Low
    highTT = tText.Range.High
    lowBT = bText.Range.Low
    highBT = bText.Range.High
    If highTT.X - lowTT.X >= highBT.X - lowBT.X Then
        LenghC = highTT.X - lowTT.X
    Else: LenghC = highBT.X - lowBT.X
    End If
    stP.X = point.X '+ CDbl(MyForm.tbDist.Text)
    stP.Y = point.Y
    stP.Z = bP.Z
    endP.X = point.X + LenghC
    endP.Y = point.Y
    endP.Z = stP.Z
    
    Set Cherta = CreateLineElement2(Nothing, stP, endP)
    ActiveModelReference.AddElement Cherta
    Cherta.Redraw
    
    ' Вычисление нового положения подписей в зависимости от длины дробной черты
    tpT.X = tpT.X + (LenghC - (highTT.X - lowTT.X)) * 0.5
    bpT.X = bpT.X + (LenghC - (highBT.X - lowBT.X)) * 0.5
    
    ' Удаление старых подписей
'    ActiveModelReference.RemoveElement bText
'    ActiveModelReference.RemoveElement tText
    
    ' создание новыйх подписей
    Set bText = CreateTextElement1(Nothing, FormatNumber(Round(bP.Z, 2), 2, vbTrue, vbTrue, vbTrue), bpT, Matrix3dIdentity)
    Set tText = CreateTextElement1(Nothing, FormatNumber(Round(tp.Z, 2), 2, vbTrue, vbTrue, vbTrue), tpT, Matrix3dIdentity)
    ActiveModelReference.AddElement bText
    ActiveModelReference.AddElement tText
    bText.Redraw
    tText.Redraw
    Set hpCell = CreateCellElement3(MyForm.cmbCell.Text, bP, True)
    
    ActiveModelReference.AddElement hpCell
    hpCell.Redraw
    
    CommandState.StartDefaultCommand

    If MyForm.cbDelLine.Value = True Then
        ActiveModelReference.RemoveElement MyLine
        MyLine.Redraw
        MyLine.Rewrite
    End If
    
End Sub

Private Sub ILocateCommandEvents_Cleanup()

End Sub

Private Sub ILocateCommandEvents_Dynamics(point As Point3d, ByVal View As View, ByVal DrawMode As MsdDrawingMode)
    Dim MyLine As LineElement ' Линия обозначающая бордюр
    Dim tp As Point3d ' Верхняя точка бордюра
    Dim bP As Point3d ' Нижняя точка борюра
    Dim tpT As Point3d ' точка вставки верхнего текста
    Dim bpT As Point3d ' точка вставки нижнего текста
    Dim tText As TextElement ' Верхняя подпись
    Dim bText As TextElement ' Нижняя подпись
    
    Dim Cherta As LineElement ' Дробная черта
    Dim stP As Point3d ' Начальная точка черты
    Dim endP As Point3d ' Конечная точка черты
    Dim LenghC As Double ' Длина черты

    Dim hpCell As CellElement ' Cell отметки высоты
    Dim HeightT As Double ' Активная высота текста
    Dim lowTT As Point3d ' Границы контэйнера верхнего текста
    Dim highTT As Point3d
    Dim lowBT As Point3d ' Границы контэнера нижнего текста
    Dim highBT As Point3d
    
    Set MyLine = SelElement
    If MyForm.cbPoint.Value = True Then
        bP = BottomPoint
        tp = TopPoint
    End If
    
    If MyLine.StartPoint.Z < MyLine.EndPoint.Z Then
        bP = MyLine.StartPoint
        tp = MyLine.EndPoint
    ElseIf MyLine.StartPoint.Z > MyLine.EndPoint.Z Then
        bP = MyLine.EndPoint
        tp = MyLine.StartPoint
    End If
    
    
    HeightT = ActiveSettings.TextStyle.Height
    ' вычисление точек вставки верхнего и нижнего текстов
    tpT.Y = point.Y + 0.1
    bpT.Y = point.Y - 0.1 - HeightT
    
    tpT.X = point.X '+ CDbl(MyForm.tbDist.Text)
    bpT.X = point.X '+ CDbl(MyForm.tbDist.Text)
    
    tpT.Z = bP.Z
    bpT.Z = bP.Z
    
    stP = bP
    stP.X = stP.X ' + CDbl(MyForm.tbDist.Text)
    
    Debug.Print HeightT
    Set bText = CreateTextElement1(Nothing, FormatNumber(Round(bP.Z, 2), 2, vbTrue, vbTrue, vbTrue), bpT, Matrix3dIdentity)
    Set tText = CreateTextElement1(Nothing, FormatNumber(Round(tp.Z, 2), 2, vbTrue, vbTrue, vbTrue), tpT, Matrix3dIdentity)
    lowTT = tText.Range.Low
    highTT = tText.Range.High
    lowBT = bText.Range.Low
    highBT = bText.Range.High
    If highTT.X - lowTT.X >= highBT.X - lowBT.X Then
        LenghC = highTT.X - lowTT.X
    Else: LenghC = highBT.X - lowBT.X
    End If
    stP.X = point.X '+ CDbl(MyForm.tbDist.Text)
    stP.Y = point.Y
    stP.Z = bP.Z
    endP.X = point.X + LenghC
    endP.Y = point.Y
    endP.Z = stP.Z
    
    Set Cherta = CreateLineElement2(Nothing, stP, endP)
    'ActiveModelReference.AddElement Cherta
    Cherta.Redraw DrawMode
    
    ' Вычисление нового положения подписей в зависимости от длины дробной черты
    tpT.X = tpT.X + (LenghC - (highTT.X - lowTT.X)) * 0.5
    bpT.X = bpT.X + (LenghC - (highBT.X - lowBT.X)) * 0.5
    
    ' Удаление старых подписей
'    ActiveModelReference.RemoveElement bText
'    ActiveModelReference.RemoveElement tText
    
    ' создание новыйх подписей
    Set bText = CreateTextElement1(Nothing, FormatNumber(Round(bP.Z, 2), 2, vbTrue, vbTrue, vbTrue), bpT, Matrix3dIdentity)
    Set tText = CreateTextElement1(Nothing, FormatNumber(Round(tp.Z, 2), 2, vbTrue, vbTrue, vbTrue), tpT, Matrix3dIdentity)
    'ActiveModelReference.AddElement bText
    'ActiveModelReference.AddElement tText
    bText.Redraw DrawMode
    tText.Redraw DrawMode
    Set hpCell = CreateCellElement3(MyForm.cmbCell.Text, bP, True)
    'ActiveModelReference.AddElement hpCell
    hpCell.Redraw DrawMode
End Sub

Private Sub ILocateCommandEvents_LocateFailed()

End Sub

Private Sub ILocateCommandEvents_LocateFilter(ByVal Element As Element, point As Point3d, Accepted As Boolean)
    Accepted = False
    'If MyForm.cbPoint.Value = True Then
       ' CommandState.StartDynamics
        'Accepted = True
   ' End If
    
    If Element.IsLineElement = True Then
        Set SelElement = Element
        Accepted = True
        ShowCommand "Отметки по бордюрю"
        ShowPrompt "Подтвердите выбор нажатием левой кнопки мыши"
        CommandState.StartDynamics
    End If
End Sub

Private Sub ILocateCommandEvents_LocateReset()
 CommandState.StartDefaultCommand
End Sub

Private Sub ILocateCommandEvents_Start()
    If MyForm.cbPoint.Value = True Then
        CommandState.StartDynamics
    End If
End Sub

Attribute VB_Name = "Module1"
Option Explicit
Public BottomPoint As Point3d
Public TopPoint As Point3d

Sub Main()
    MyForm.Show vbModeless
End Sub

Attribute VB_Name = "MyForm"
Attribute VB_Base = "0{B01B5306-CF64-4B32-B812-86A4F4DAA142}{F71110CE-BEEE-40CE-88E6-062681A11566}"
Attribute VB_GlobalNameSpace = False
Attribute VB_Creatable = False
Attribute VB_PredeclaredId = True
Attribute VB_Exposed = False
Attribute VB_TemplateDerived = False
Attribute VB_Customizable = False
Option Explicit



Private Sub cmbCreateHP_Click()
    If cbPoint.Value = True Then
        CommandState.StartPrimitive New PCE_place_points, True
    ElseIf cbPoint.Value = False Then
        CommandState.StartLocate New LCE_HP_by_border
    End If
    
End Sub


Private Sub TextBox_post_chislitel_Change()

End Sub

Private Sub UserForm_Initialize()
    Dim MyCellEnum As CellInformationEnumerator
    Dim MyCell As CellInformation
    Set MyCellEnum = Application.GetCellInformationEnumerator(True, False)
    If IsCellLibraryAttached Then
        Set MyCellEnum = Application.GetCellInformationEnumerator(False, False)
        While MyCellEnum.MoveNext
            Set MyCell = MyCellEnum.Current
            cmbCell.AddItem MyCell.Name
        Wend
        Else: MsgBox "Библиотека Cell не подключена", vbOKOnly
    End If
End Sub

Attribute VB_Name = "PCE_place_points"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private FirstPoint As Boolean
Private PPpoint As Boolean
Private i As Integer
'Private bP As Point3d
'Private tp As Point3d
Private Cherta As LineElement ' Дробная черта
Private tText As TextElement ' Верхняя подпись
Private bText As TextElement
Private hpCell As CellElement
Private bRotate As Boolean
Private mText As CellElement
Private InsertPoint As Point3d
Private tempCell As CellElement
Implements IPrimitiveCommandEvents

Private Sub IPrimitiveCommandEvents_Cleanup()

End Sub

Private Sub IPrimitiveCommandEvents_DataPoint(point As Point3d, ByVal View As View)
    Dim MyLine As LineElement ' Линия обозначающая бордюр
'
    If FirstPoint = False And PPpoint = False Then
        i = 0
        BottomPoint = point
        FirstPoint = True
        bRotate = False
        i = i + 1
        If MyForm.CheckBox_One_Point Then
            FirstPoint = False
            PPpoint = True
            i = i + 1
            
            CommandState.StartDynamics
        End If
    ElseIf FirstPoint = True And PPpoint = False Then
        i = i + 1
        TopPoint = point
        FirstPoint = False
        CommandState.StartDynamics
        
        PPpoint = True
    End If
    
    If PPpoint = True And FirstPoint = False Then
        i = i + 1
        If i > 3 Then
        
        If MyForm.CheckBox_rotate Then
            If bRotate = False Then
                bRotate = True
                InsertPoint = point
                InsertPoint.Z = 0
            Else
                GetCellElement tempCell
                CommandState.StopDynamics
            End If
        Else
            GetCellElement mText
            CommandState.StopDynamics
        End If
        
       

        End If
    End If
End Sub

Private Sub IPrimitiveCommandEvents_Dynamics(point As Point3d, ByVal View As View, ByVal DrawMode As MsdDrawingMode)
    Dim tp As Point3d ' Верхняя точка бордюра
    Dim bP As Point3d ' Нижняя точка борюра
    Dim tpT As Point3d ' точка вставки верхнего текста
    Dim bpT As Point3d ' точка вставки нижнего текста
    Dim stP As Point3d ' Начальная точка черты
    Dim endP As Point3d ' Конечная точка черты
    Dim LenghC As Double ' Длина черты

    Dim hpCell As CellElement ' Cell отметки высоты
    Dim HeightT As Double ' Активная высота текста
    Dim lowTT As Point3d ' Границы контэйнера верхнего текста
    Dim highTT As Point3d
    Dim lowBT As Point3d ' Границы контэнера нижнего текста
    Dim highBT As Point3d
  
    bP = BottomPoint
    tp = TopPoint
       
    HeightT = ActiveSettings.TextStyle.Height
    ' вычисление точек вставки верхнего и нижнего текстов
    
    
    If Not (MyForm.CheckBox_rotate And bRotate) Then
        tpT.Y = point.Y + HeightT * 0.2
        bpT.Y = point.Y - HeightT * 1.2
        
        tpT.X = point.X '+ CDbl(MyForm.tbDist.Text)
        bpT.X = point.X '+ CDbl(MyForm.tbDist.Text)
        bpT.Z = 0
        tpT.Z = 0
        stP = bP
        stP.X = stP.X ' + CDbl(MyForm.tbDist.Text)
        
        Set tText = CreateTextElement1(Nothing, MyForm.TextBox_post_znamenatel.Text & FormatNumber(Round(tp.Z, 2), 2, vbTrue, vbTrue, vbTrue), bpT, Matrix3dIdentity)
        Set bText = CreateTextElement1(Nothing, MyForm.TextBox_post_chislitel.Text & FormatNumber(Round(bP.Z, 2), 2, vbTrue, vbTrue, vbTrue), tpT, Matrix3dIdentity)
            
        lowTT = tText.Range.Low
        highTT = tText.Range.High
        lowBT = bText.Range.Low
        highBT = bText.Range.High
            If highTT.X - lowTT.X >= highBT.X - lowBT.X Then
                LenghC = highTT.X - lowTT.X
            Else: LenghC = highBT.X - lowBT.X
            End If
        stP.X = point.X '+ CDbl(MyForm.tbDist.Text)
        stP.Y = point.Y
        stP.Z = 0
        endP.X = point.X + LenghC
        endP.Y = point.Y
        endP.Z = 0
            
            If MyForm.CheckBox_Align_center Then
                ' Вычисление нового положения подписей в зависимости от длины дробной черты
                tpT.X = tpT.X + (LenghC - (highTT.X - lowTT.X)) * 0.5
                bpT.X = bpT.X + (LenghC - (highBT.X - lowBT.X)) * 0.5
                
                ' создание новыйх подписей
                Set bText = CreateTextElement1(Nothing, FormatNumber(Round(bP.Z, 2), 2, vbTrue, vbTrue, vbTrue) & MyForm.TextBox_post_chislitel.Text, bpT, Matrix3dIdentity)
                Set tText = CreateTextElement1(Nothing, FormatNumber(Round(tp.Z, 2), 2, vbTrue, vbTrue, vbTrue) & MyForm.TextBox_post_znamenatel.Text, tpT, Matrix3dIdentity)
            End If
        
        Set Cherta = CreateLineElement2(Nothing, stP, endP)
'        Cherta.Redraw DrawMode
'        bText.Redraw DrawMode
'        tText.Redraw DrawMode
        
        If MyForm.CheckBox_Place_znak Then
            Set hpCell = CreateCellElement3(MyForm.cmbCell.Text, bP, True)
            hpCell.Redraw DrawMode
        End If
        
        
        Dim arr(0 To 3) As Element
        Set arr(0) = bText
        If Not MyForm.CheckBox_One_Point Then
            Set arr(1) = tText
            Set arr(2) = Cherta
        End If
        Set mText = CreateCellElement1("hText", arr, Point3dFromXYZ(point.X, point.Y, 0), False)
        mText.Redraw DrawMode
        
        If MyForm.CheckBox_level_m2000 Then
            mText.ScaleAll mText.Origin, 2, 2, 2
            mText.Redraw DrawMode
            mText.ScaleAll mText.Origin, 0.5, 0.5, 0.5
        End If
        
        
    Else
        Dim RotationMatrix As Matrix3d
        Dim templine As LineElement
        Dim Eltrans As Transform3d
        
'        Set templine = CreateLineElement2(Nothing, mText.Origin, Point3dFromXYZ(point.X, point.Y, 0))
'        templine.Redraw DrawMode
        
        
        
        Set tempCell = mText.Clone
'        If MyForm.CheckBox_level_m2000 Then
'            tempCell.ScaleAll tempCell.Origin, 0.5, 0.5, 0.5
'        End If
        
        RotationMatrix = Matrix3dFromAxisAndRotationAngle(2, GAngle(mText.Origin, Point3dFromXYZ(point.X, point.Y, 0)))
        Eltrans = Transform3dFromMatrix3dAndFixedPoint3d(RotationMatrix, mText.Origin)
        tempCell.Transform Eltrans
        tempCell.Redraw DrawMode
        If MyForm.CheckBox_level_m2000 Then
            tempCell.ScaleAll tempCell.Origin, 2, 2, 2
            tempCell.Redraw DrawMode
            tempCell.ScaleAll tempCell.Origin, 0.5, 0.5, 0.5
        End If
        
      '  Dim arr(0 To 3) As Element
'        Dim mText As CellElement
'        Set mText = CreateCellElement1(hText, Array(bText, tText, Cherta), point)
'        mText.Redraw DrawMode
        
    End If
End Sub

Private Sub IPrimitiveCommandEvents_Keyin(ByVal Keyin As String)

End Sub

Private Sub IPrimitiveCommandEvents_Reset()
    CommandState.StartDefaultCommand

End Sub

Private Sub IPrimitiveCommandEvents_Start()

End Sub

Private Sub GetCellElement(mCell As CellElement)
    Dim mElemet As ElementEnumerator
    
    
    If MyForm.CheckBox_Drop_cell Then
        Set mElemet = mCell.GetSubElements
        While mElemet.MoveNext
            If MyForm.CheckBox_level_m1000 Then
                DrawElement mElemet.Current, MyForm.TextBox_level_m1000.Text
            End If
            
        Wend
        If MyForm.CheckBox_level_m2000 Then
            mCell.ScaleAll mCell.Origin, 2, 2, 2
            Set mElemet = mCell.GetSubElements
                While mElemet.MoveNext
                    If MyForm.CheckBox_level_m2000 Then
                        DrawElement mElemet.Current, MyForm.TextBox_level_m2000.Text
                    End If
                Wend
        End If
    Else
        If MyForm.CheckBox_level_m1000 Then
            DrawElement mCell, MyForm.TextBox_level_m1000.Text
        End If
        If MyForm.CheckBox_level_m2000 Then
            mCell.ScaleAll mCell.Origin, 2, 2, 2
            DrawElement mCell, MyForm.TextBox_level_m2000.Text
        End If
        
    End If
    
End Sub

Private Sub DrawElement(mElement As Element, LevelName As String)
    mElement.Level = CheckLevel(LevelName)
    ActiveModelReference.AddElement mElement
    mElement.Redraw
End Sub

Function GAngle(pSt As Point3d, pEnd As Point3d) As Double
Dim dAng As Double
Dim Angel As Double
Dim ang As Double
Dim dx As Double
Dim dy As Double
dx = pEnd.X - pSt.X
dy = pEnd.Y - pSt.Y
If dy <> 0 Then
    ang = Atn(dx / dy)
    If dx >= 0 And dy > 0 Then
        dAng = ang
    ElseIf dx >= 0 And dy < 0 Then
        dAng = ang + Pi
    ElseIf dx < 0 And dy < 0 Then
        dAng = ang + Pi
    ElseIf dx < 0 And dy > 0 Then
        dAng = ang + 2 * Pi
    End If
ElseIf dy = 0 Then

    If dx > 0 Then
        dAng = Pi / 2
    ElseIf dx < 0 Then
        dAng = 3 * Pi / 4
    End If
End If
Angel = Pi / 2 - dAng
GAngle = Angel
End Function

Function SecondRotate(dView As View, rotPoint As Point3d) As Transform3d
    Dim plan        As Plane3d
    Dim myRot       As Matrix3d
    Dim pntTemp     As Point3d
    Dim PerpVector  As Vector3d
    Dim tmpVector   As Vector3d
    Dim prBpoint    As Point3d
    
  '  If FirstPoint = True And Second = False Then
        With fdPoint
            .X = bPoint.X
            .Y = bPoint.Y
            .Z = 0
        End With
  '  End If
    
    prBpoint = bPoint
    prBpoint.Z = 0
    
    plan.Origin = fdPoint
    plan.Normal = dView.Rotation.RowZ
    
    If fdPoint.X <> bPoint.X And fdPoint.Y <> bPoint.Y Then
        plan.Normal = Point3dFromVector3d(Vector3dCrossProduct(Vector3dUnitPerpendicularXY(Vector3dFromPoint3d(Point3dSubtract(fdPoint, bPoint))), Vector3dSubtractPoint3dPoint3d(fdPoint, bPoint)))
    End If
    prPointOnPlan = Point3dProjectToPlane3d(rotPoint, plan)
    myRot = Matrix3dFromRotationBetweenVectors(Point3dSubtract(prBpoint, bPoint), Point3dSubtract(prPointOnPlan, bPoint))
    SecondRotate = Transform3dFromMatrix3dAndFixedPoint3d(myRot, bPoint)
    
End Function

Function CheckLevel(LevelName As String) As Level
    Dim MyLevel As Level
    On Error Resume Next
    
    Set CheckLevel = ActiveDesignFile.Levels(LevelName)
    If Err.Number <> 0 And LevelName <> "" Then
         Set MyLevel = ActiveDesignFile.AddNewLevel(LevelName)
         ActiveDesignFile.Levels.Rewrite
         MsgBox "Создан слой: " & LevelName
         Set CheckLevel = MyLevel
    End If
    Err.Clear
End Function
