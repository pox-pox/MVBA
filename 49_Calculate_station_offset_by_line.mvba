Attribute VB_Name = "LCE_Line_Snap"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private mElement As Element
Private Join As Boolean
Private okPoint As Point3d
Private station As String
Private offset As String
Private stPoint As pointVertex
Private endPoint As pointVertex

Private Sub ILocateCommandEvents_Accept(ByVal Element As Element, point As Point3d, ByVal View As View)
    If UserForm1.CheckBox_calc_by_level Then
        Dim startStation As Double
        Dim dStation As Double
        Dim endStation As Double
        Dim myEnum As ElementEnumerator
        Dim myFilter As New ElementScanCriteria
        Dim mLabel As TextElement
        Dim sOffset As Double
        
        Dim mArea As Double
        Dim PerpendPoint As Point3d
        Dim PerpendPointEnd As Point3d
        
        Dim xlAPP As Excel.Application
        Dim xlBook As Excel.Workbook
        Dim WS As Excel.Worksheet

        
        
        Dim i As Long
        i = 1
        
        myFilter.ExcludeAllLevels
        myFilter.ExcludeAllTypes

        myFilter.IncludeType msdElementTypeLineString
        myFilter.IncludeType msdElementTypeLine
        myFilter.IncludeType msdElementTypeShape
        myFilter.IncludeType msdElementTypeComplexShape
        myFilter.IncludeType msdElementTypeSharedCell
        myFilter.IncludeType msdElementTypeCellHeader
        myFilter.IncludeLevel ActiveDesignFile.Levels.Find(UserForm1.ComboBox_level_of_obj.Text)
        
        If UserForm1.CheckBox_InsideBufer Then
            ClipFence myEnum
        Else
            Set myEnum = ActiveModelReference.Scan(myFilter)
        End If
        
        If getEnumeratorCount(myEnum) > 0 Then
            
            Set xlAPP = CreateObject("Excel.Application")
            Set xlBook = xlAPP.Workbooks.Add
            Set WS = xlBook.Worksheets(1)
               
        
        
                While myEnum.MoveNext
                    Dim stStation As String
                    Dim enStation As String
                    If Not (myEnum.Current.Level Is Nothing) Then
                    Debug.Print myEnum.Current.Level.Name
                    
                    If myEnum.Current.Level.Name = UserForm1.ComboBox_level_of_obj.Text Then
                        Select Case myEnum.Current.Type
                            Case msdElementTypeComplexShape
                                Dim tempShape As ShapeElement
                                Set tempShape = ComplexShapeToShape(myEnum.Current.AsComplexShapeElement)
                                GetParamFromObj mElement.AsLineElement, tempShape, mArea
                                DrawOffset mElement.AsLineElement, stPoint.origin, PerpendPoint
                                DrawLabel "station= " & CStr(FormatNumber(Round(stPoint.station, 1), 1, vbTrue, vbTrue, vbTrue)) & " S= " & CStr(FormatNumber(Round(mArea, 1), 1, vbTrue, vbTrue, vbTrue)), stPoint.origin, PerpendPoint
                                sOffset = FormatNumber(Round(SideOffset(mElement, stPoint.origin), 1), 1, vbTrue, vbTrue, vbTrue)
                                DrawOffset mElement.AsLineElement, endPoint.origin, PerpendPoint
                                
                                DrawLabel "station= " & CStr(FormatNumber(Round(endPoint.station, 1), 1, vbTrue, vbTrue, vbTrue)) & " S= " & CStr(FormatNumber(Round(mArea, 1), 1, vbTrue, vbTrue, vbTrue)), endPoint.origin, PerpendPoint
                            Case msdElementTypeShape
                                GetParamFromObj mElement.AsLineElement, myEnum.Current, mArea
                                DrawOffset mElement.AsLineElement, stPoint.origin, PerpendPoint
                                DrawLabel "station= " & CStr(FormatNumber(Round(stPoint.station, 1), 1, vbTrue, vbTrue, vbTrue)) & " S= " & CStr(FormatNumber(Round(mArea, 1), 1, vbTrue, vbTrue, vbTrue)), stPoint.origin, PerpendPoint
                                DrawOffset mElement.AsLineElement, endPoint.origin, PerpendPoint
                                sOffset = FormatNumber(Round(SideOffset(mElement, stPoint.origin), 1), 1, vbTrue, vbTrue, vbTrue)
                                DrawLabel "station= " & CStr(FormatNumber(Round(endPoint.station, 1), 1, vbTrue, vbTrue, vbTrue)) & " S= " & CStr(FormatNumber(Round(mArea, 1), 1, vbTrue, vbTrue, vbTrue)), endPoint.origin, PerpendPoint
                            Case msdElementTypeLineString
                                GetParamFromObj mElement.AsLineElement, myEnum.Current, mArea
                                DrawOffset mElement.AsLineElement, stPoint.origin, PerpendPoint
                                DrawLabel "station= " & CStr(FormatNumber(Round(stPoint.station, 1), 1, vbTrue, vbTrue, vbTrue)) & " S= " & CStr(FormatNumber(Round(mArea, 1), 1, vbTrue, vbTrue, vbTrue)), stPoint.origin, PerpendPoint
                                DrawOffset mElement.AsLineElement, endPoint.origin, PerpendPoint
                                sOffset = FormatNumber(Round(SideOffset(mElement, stPoint.origin), 1), 1, vbTrue, vbTrue, vbTrue)
                                DrawLabel "station= " & CStr(FormatNumber(Round(endPoint.station, 1), 1, vbTrue, vbTrue, vbTrue)) & " S= " & CStr(FormatNumber(Round(mArea, 1), 1, vbTrue, vbTrue, vbTrue)), endPoint.origin, PerpendPoint
                               
                            Case msdElementTypeLine
                                If Point3dEqual(myEnum.Current.AsLineElement.startPoint, myEnum.Current.AsLineElement.endPoint) Then
                                    stPoint.station = GetStation(mElement.AsLineElement, myEnum.Current.AsLineElement.startPoint)
                                    endPoint.station = stPoint.station
                                    DrawOffset mElement.AsLineElement, myEnum.Current.AsLineElement.startPoint, PerpendPoint
                                    sOffset = FormatNumber(Round(SideOffset(mElement, myEnum.Current.AsLineElement.startPoint), 1), 1, vbTrue, vbTrue, vbTrue)
                                    DrawLabel "station= " & CStr(FormatNumber(Round(stPoint.station, 1), 1, vbTrue, vbTrue, vbTrue)) & " offset=" & sOffset, myEnum.Current.AsLineElement.startPoint, PerpendPoint
                                Else
                                    GetParamFromObj mElement.AsLineElement, myEnum.Current, mArea
                                    DrawOffset mElement.AsLineElement, stPoint.origin, PerpendPoint
                                    sOffset = FormatNumber(Round(SideOffset(mElement, stPoint.origin), 1), 1, vbTrue, vbTrue, vbTrue)
                                    stStation = CStr(FormatNumber(Round(stPoint.station, 1), 1, vbTrue, vbTrue, vbTrue))
                                    enStation = CStr(FormatNumber(Round(endPoint.station, 1), 1, vbTrue, vbTrue, vbTrue))
                                    DrawLabel "st.= " & stStation & " S= " & CStr(FormatNumber(Round(mArea, 1), 1, vbTrue, vbTrue, vbTrue)), stPoint.origin, PerpendPoint
                                    DrawOffset mElement.AsLineElement, endPoint.origin, PerpendPoint
                                    DrawLabel "station= " & enStation & " S= " & CStr(FormatNumber(Round(mArea, 1), 1, vbTrue, vbTrue, vbTrue)), endPoint.origin, PerpendPoint
                                End If
                            Case msdElementTypeSharedCell
                                
                                stPoint.station = GetStation(mElement.AsLineElement, myEnum.Current.AsSharedCellElement.origin)
                                DrawOffset mElement.AsLineElement, myEnum.Current.AsSharedCellElement.origin, PerpendPoint
                                sOffset = FormatNumber(Round(SideOffset(mElement, myEnum.Current.AsSharedCellElement.origin), 1), 1, vbTrue, vbTrue, vbTrue)
                                DrawLabel CStr(FormatNumber(Round(stPoint.station, 1), 1, vbTrue, vbTrue, vbTrue)), myEnum.Current.AsSharedCellElement.origin, PerpendPoint
                               ' Dim mValue As String
                               ' mValue = GetTagValue(myEnum.Current.AsSharedCellElement)
                            Case msdElementTypeCellHeader
                                Dim cellEnum As ElementEnumerator
                                Dim mShape As ShapeElement
                                Set cellEnum = myEnum.Current.AsCellElement.GetSubElements
                                    While cellEnum.MoveNext
                                        Set mShape = ComplexShapeToShape(cellEnum.Current.AsComplexShapeElement)
                                    Wend
                                GetParamFromObj mElement.AsLineElement, mShape, mArea
                                DrawOffset mElement.AsLineElement, stPoint.origin, PerpendPoint
                                DrawLabel "station= " & CStr(FormatNumber(Round(stPoint.station, 1), 1, vbTrue, vbTrue, vbTrue)) & " S= " & CStr(FormatNumber(Round(mArea, 1), 1, vbTrue, vbTrue, vbTrue)), stPoint.origin, PerpendPoint
                                DrawOffset mElement.AsLineElement, endPoint.origin, PerpendPoint
                                sOffset = FormatNumber(Round(SideOffset(mElement, stPoint.origin), 1), 1, vbTrue, vbTrue, vbTrue)
                                DrawLabel "station= " & CStr(FormatNumber(Round(endPoint.station, 1), 1, vbTrue, vbTrue, vbTrue)) & " S= " & CStr(FormatNumber(Round(mArea, 1), 1, vbTrue, vbTrue, vbTrue)), endPoint.origin, PerpendPoint
                                
                        End Select
                        WS.Cells(i, 1) = CStr(FormatNumber(Round(stPoint.station, 1), 1, vbTrue, vbTrue, vbTrue))
                        WS.Cells(i, 2) = CStr(FormatNumber(Round(endPoint.station, 1), 1, vbTrue, vbTrue, vbTrue))
                        WS.Cells(i, 3) = mArea
                        WS.Cells(i, 5) = GetAtr(myEnum.Current)
                        If sOffset > 0 Then
                            WS.Cells(i, 4) = "чет."
                        Else
                            WS.Cells(i, 4) = "нечет."
                        End If
                        i = i + 1
                        
                    End If
                    End If
                Wend
                xlBook.SaveAs Filename:=ActiveDesignFile.Path & "\" & "Table_1_" & ".xlsx"
                        xlBook.Save1
                        xlAPP.Quit
        End If
    Else
        ClearClipboard
        SetTextIntoClipboard station
        CommandState.StartDynamics
    End If
    CommandState.StartDefaultCommand
End Sub
Private Function GetAtr(mElem As Element) As String
    Dim oPH As PropertyHandler
    Set oPH = CreatePropertyHandler(mElem)
    Dim mStrings() As String
    Dim mString As String
    
    mStrings = oPH.GetAccessStrings
    ShowDisplayString oPH, mStrings(0), mString
    GetAtr = mString
End Function


Private Sub ShowDisplayString(oPH As PropertyHandler, accessString As String, mValue As String)
    On Error GoTo HandleError
    
    If Not oPH.SelectByAccessString(accessString) Then
        Debug.Print "NOT FOUND!!"
    Else
        mValue = CStr(oPH.GetValue)
        Debug.Print oPH.GetValue
    End If
    
    Exit Sub
HandleError:
    Debug.Print Err.Description
End Sub
Function GetTagValue(mShared As SharedCellElement) As String
    Dim mTag As TagElement
    Dim sharedEnum As ElementEnumerator
    
    Set sharedEnum = mShared.GetSubElements
    Debug.Print getEnumeratorCount(sharedEnum)
    While sharedEnum.MoveNext
        If sharedEnum.Current.Type = msdElementTypeTag Then
            GetTagValue = CStr(sharedEnum.Current.AsTagElement.Value)
            Debug.Print CStr(sharedEnum.Current.AsTagElement.Value)
        End If
    Wend
    
End Function
Function getEnumeratorCount(oEnumerator As ElementEnumerator) As Long
    Dim count As Long
    With oEnumerator
        .Reset
        Do While .MoveNext
            count = count + 1
        Loop
        .Reset
    End With
    getEnumeratorCount = count
End Function

Private Sub ExportExcel(expStationStart As Double, expStationEnd As Double, expOffset As Double)
    ' Excel Application, workbook, and sheet object
    Dim xlAPP As Excel.Application
    Dim xlBook As Excel.Workbook
    Dim xlSheet As Object
    
    Set xlAPP = CreateObject("Excel.Application")
    xlAPP.Visible = False
    Set xlBook = xlAPP.Workbooks.Add
    Set xlSheet = xlBook.Sheets(1)
    
    
End Sub
Private Sub ClipFence(CutEnum As ElementEnumerator)
    Dim fnc As Fence
    Dim saveClip As Boolean
    Dim saveOverlap As Boolean
    Dim saveVoid As Boolean
'    Dim ee As ElementEnumerator
    Dim myView As View
    
    Dim myEnum As ElementEnumerator
    Dim mFilter As New ElementScanCriteria
    Dim i As Long
    
    Dim myFences() As Element
    
    mFilter.ExcludeAllLevels
    mFilter.ExcludeAllTypes
    
    mFilter.IncludeLevel ActiveDesignFile.Levels.Find(UserForm1.ComboBox_LevelBuffer)
    mFilter.IncludeType msdElementTypeShape
'    mFilter.IncludeType msdElementTypeComplexShape
'    mFilter.IncludeType msdElementTypeCellHeader
    
    Set myEnum = ActiveModelReference.Scan(mFilter)
    
    myFences = myEnum.BuildArrayFromContents
    
    Set myView = ActiveDesignFile.Views(1)
    Set fnc = ActiveDesignFile.Fence
    
    With ActiveSettings
        
        saveClip = .FenceClip
        .FenceClip = True
        saveOverlap = .FenceOverlap
        .FenceOverlap = False
        saveVoid = .FenceVoid
        .FenceVoid = False
    End With
    
    ActiveModelReference.Levels.Find(UserForm1.ComboBox_LevelBuffer).IsDisplayed = False
    
    For i = 0 To UBound(myFences)
        fnc.DefineFromElement myView, myFences(i)
        If Not fnc.IsDefined Then
            ShowError "The fence is not defined"
            Exit Sub
        End If
        Set CutEnum = fnc.GetContents(False)
'        While ee.MoveNext
'            ActiveModelReference.RemoveElement ee.Current
'            ee.Current.Redraw
'        Wend
    Next i
    
    fnc.Undefine
    ActiveModelReference.Levels.Find(UserForm1.ComboBox_LevelBuffer).IsDisplayed = True
    
    With ActiveSettings
            .FenceClip = saveClip
            .FenceOverlap = saveOverlap
            .FenceVoid = saveVoid
        End With
    
End Sub
Function ComplexShapeToShape(CShape As Element) As ShapeElement
    Dim myEnum As ElementEnumerator
    Dim MyShape As ShapeElement
    Dim Verteces() As Point3d
    Dim i As Integer
    ReDim Verteces(0)
    If CShape.IsComplexShapeElement Then
        Set myEnum = CShape.AsComplexShapeElement.GetSubElements
            While myEnum.MoveNext
                For i = 0 To UBound(myEnum.Current.AsVertexList.GetVertices)
                    Verteces(UBound(Verteces)) = myEnum.Current.AsLineElement.Vertex(i + 1)
                    ReDim Preserve Verteces(UBound(Verteces) + 1)
                Next i
                ReDim Preserve Verteces(UBound(Verteces) - 1)
            Wend
     '   CShape.IsSnappable = True
        Set MyShape = CreateShapeElement1(CShape, Verteces, msdFillModeNotFilled)
        MyShape.IsSnappable = True
        Set ComplexShapeToShape = MyShape
    ElseIf CShape.IsShapeElement Then
        Set ComplexShapeToShape = CShape.AsShapeElement
    End If
End Function
Private Sub DrawLabel(mText As String, mOrigin As Point3d, targetPoint As Point3d)
    Dim mLabel As TextElement
    Dim RotationMatrix As Matrix3d
    Dim rOtmetki As Double
    
    rOtmetki = AngleTxt(mOrigin, targetPoint) + Pi
    RotationMatrix = Matrix3dFromAxisAndRotationAngle(2, rOtmetki)
    
    Set mLabel = CreateTextElement1(Nothing, mText, mOrigin, RotationMatrix)
    mLabel.Level = CheckLevel(UserForm1.TextBox_Level_Mark.Text)
    mLabel.TextStyle.Justification = msdTextJustificationLeftBottom
    mLabel.TextStyle.Font = ActiveDesignFile.Fonts("Arial")
    mLabel.TextStyle.Height = 0.5
    mLabel.TextStyle.Width = 0.5
    mLabel.Color = 2
    ActiveModelReference.AddElement mLabel
    mLabel.Redraw
    
End Sub

Function CheckLevel(LevelName As String) As Level
    Dim MyLevel As Level
    On Error Resume Next
    
    Set CheckLevel = ActiveDesignFile.Levels(LevelName)
    If Err.Number <> 0 And LevelName <> "" Then
         Set MyLevel = ActiveDesignFile.AddNewLevel(LevelName)
         ActiveDesignFile.Levels.Rewrite
         MsgBox "Создан слой: " & LevelName
         Set CheckLevel = MyLevel
    End If
    Err.Clear
End Function
Public Sub SetTextIntoClipboard(ByVal txt As String)
    Dim MyDataObj As New DataObject
    MyDataObj.SetText txt
    MyDataObj.PutInClipboard
End Sub
Public Sub ClearClipboard()
    Dim MyDataObj As New DataObject
    MyDataObj.SetText "": MyDataObj.PutInClipboard
End Sub
Private Sub ILocateCommandEvents_Cleanup()

End Sub
Private Function mRound(mNum As Double, r As Integer) As Double
  mRound = FormatNumber(Round(mNum, r), r, vbTrue, vbTrue, vbFalse)
End Function
Private Sub ILocateCommandEvents_Dynamics(point As Point3d, ByVal View As View, ByVal DrawMode As MsdDrawingMode)
    Dim prPoint As Point3d
    Dim perpend As LineElement
    Dim jOk As TextElement
    Dim SO As TextElement
    If Join = False Then
        prPoint = Project_Point1(mElement, point)
        Set perpend = CreateLineElement2(Nothing, point, prPoint)
        station = CStr(FormatNumber(Round(mElement.AsLineElement.DistanceAtPoint(point), 1), 1, vbTrue, vbTrue, vbTrue))
        UserForm1.Label_Station.Caption = "Station= " & station
        Set SO = CreateTextElement1(Nothing, station, point, Matrix3dIdentity)
        
        perpend.LineWeight = 0
        perpend.Color = 4
        perpend.Redraw DrawMode
        SO.Redraw DrawMode
    ElseIf Join = True Then
        Set jOk = CreateTextElement1(Nothing, "OK", okPoint, Matrix3dIdentity)
        jOk.TextStyle.Height = 0.1
        jOk.TextStyle.Width = 0.1
        jOk.Redraw DrawMode
    End If
    
End Sub

Private Sub ILocateCommandEvents_LocateFailed()
   ' CommandState.StartDynamics
End Sub

Private Sub ILocateCommandEvents_LocateFilter(ByVal Element As Element, point As Point3d, Accepted As Boolean)
Dim k As Long
Accepted = False
    If Element.IsLineElement Then
            Accepted = True
            Set mElement = Element
            mElement.Transform Transform3dFromMatrix3dPoint3d(Matrix3dFromScaleFactors(1, 1, 0), Point3dFromXYZ(0, 0, 0)) ''''' Линия в 2D
            CommandState.StartDynamics
            Join = False
        End If

End Sub

Private Sub ILocateCommandEvents_LocateReset()
    CommandState.StopDynamics
    CommandState.StartDefaultCommand
End Sub

Private Sub ILocateCommandEvents_Start()
    ShowCommand "Snap"
    ShowPrompt "Укажите ось"
End Sub

Private Function Project_Point1(mLine As Element, mPoint As Point3d) As Point3d
    Dim mComplexStr As ElementEnumerator
    Dim i As Long
    Dim j As Long
    Dim minDist As Double
    Dim tmpDist As Double
    Dim tmpP As Point3d
        Select Case mLine.Type
            Case msdElementTypeLineString
                minDist = 500000
                    tmpP = mPoint
                    i = mLine.AsLineElement.GetClosestSegment(tmpP)
                    tmpP.Z = mLine.AsLineElement.Vertex(i + 1).Z * 0.5 + mLine.AsLineElement.Vertex(i + 2).Z * 0.5
    
                    tmpDist = Dist_Segment_to_Point(mLine.AsLineElement.Vertex(i + 1), mLine.AsLineElement.Vertex(i + 2), tmpP)
                        If tmpDist < minDist Then
                            minDist = tmpDist
                            Project_Point1 = Project_Point(mLine.AsLineElement.Vertex(i + 1), mLine.AsLineElement.Vertex(i + 2), tmpP)
                        End If
            Case msdElementTypeComplexString
                Set mComplexStr = mLine.AsComplexStringElement.GetSubElements
                    minDist = 5000000
                    While mComplexStr.MoveNext
                        Select Case mComplexStr.Current.Type
                            Case msdElementTypeLineString
                                tmpP = mPoint
                                i = mComplexStr.Current.AsLineElement.GetClosestSegment(tmpP)
                                tmpP.Z = mComplexStr.Current.AsLineElement.Vertex(i + 1).Z * 0.5 + mComplexStr.Current.AsLineElement.Vertex(i + 2).Z * 0.5
                                tmpDist = Dist_Segment_to_Point(mComplexStr.Current.AsLineElement.Vertex(i + 1), mComplexStr.Current.AsLineElement.Vertex(i + 2), tmpP)
                                    If tmpDist < minDist Then
                                        minDist = tmpDist
                                        Project_Point1 = Project_Point(mComplexStr.Current.AsLineElement.Vertex(i + 1), mComplexStr.Current.AsLineElement.Vertex(i + 2), tmpP)
                                    End If
                            Case msdElementTypeLine
                                tmpP = mPoint
                                tmpP.Z = mComplexStr.Current.AsLineElement.startPoint.Z
                                tmpDist = Dist_Segment_to_Point(mComplexStr.Current.AsLineElement.startPoint, mComplexStr.Current.AsLineElement.endPoint, tmpP)
                                    If tmpDist < minDist Then
                                    minDist = tmpDist
                                    Project_Point1 = Project_Point(mComplexStr.Current.AsLineElement.startPoint, mComplexStr.Current.AsLineElement.endPoint, tmpP)
                                End If
                        End Select
                    Wend
        End Select
End Function
Private Function SideOffset(mLine As Element, mPoint As Point3d) As Double
    Dim i As Long
    Dim mSpan As Vector3d
    Dim mOffset As Vector3d
    Dim prPoint As Point3d
    
    i = mLine.AsLineElement.GetClosestSegment(mPoint)
    mSpan = Vector3dSubtractPoint3dPoint3d(mLine.AsLineElement.Vertex(i + 2), mLine.AsLineElement.Vertex(i + 1))
    prPoint = Project_Point1(mLine, mPoint)
    mOffset = Vector3dSubtractPoint3dPoint3d(prPoint, mPoint)
    
    SideOffset = Vector3dAngleBetweenVectorsXY(mSpan, mOffset)

End Function
Private Function Dist_Segment_to_Point(startPoint As Point3d, endPoint As Point3d, iPoint As Point3d) As Double
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    Dim tmpL As LineElement
    vPoint = Vector3dSubtractPoint3dPoint3d(iPoint, startPoint)
    vLine = Vector3dSubtractPoint3dPoint3d(endPoint, startPoint)
    
    c1 = Vector3dDotProduct(vPoint, vLine)
    c2 = Vector3dDotProduct(vLine, vLine)
        If c1 <= 0 Then
            Dist_Segment_to_Point = Point3dDistance(startPoint, iPoint)
        ElseIf c2 <= c1 Then
            Dist_Segment_to_Point = Point3dDistance(endPoint, iPoint)
        Else
            k = c1 / c2
            vProject = Vector3dScale(vLine, k)
            pProject = Vector3dAdd(Vector3dFromPoint3d(startPoint), vProject)
            Dist_Segment_to_Point = Point3dDistance(Point3dFromVector3d(pProject), iPoint)
        End If
End Function
Private Function Project_Point(startPoint As Point3d, endPoint As Point3d, iPoint As Point3d) As Point3d
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    
    vPoint = Vector3dSubtractPoint3dPoint3d(iPoint, startPoint)
    vLine = Vector3dSubtractPoint3dPoint3d(endPoint, startPoint)
    
    c1 = Vector3dDotProduct(vPoint, vLine)
    c2 = Vector3dDotProduct(vLine, vLine)
        If c1 <= 0 Then
            Project_Point = startPoint
        ElseIf c2 <= c1 Then
            Project_Point = endPoint
        Else
            k = c1 / c2
            vProject = Vector3dScale(vLine, k)
            Project_Point = Point3dFromVector3d(Vector3dAdd(Vector3dFromPoint3d(startPoint), vProject))
        End If
End Function

Function GetClosestSegment3d(iLine As LineElement, iPoint As Point3d) As Point3d()
    Dim i As Long
    Dim Segment(0 To 1) As Point3d ' 0 - start , 1 - end
    i = iLine.GetClosestVertex(iPoint)
        If i = 0 Then
            Segment(0) = iLine.Vertex(1)
            Segment(1) = iLine.Vertex(2)
        ElseIf i = (iLine.VerticesCount - 1) Then
            Segment(0) = iLine.Vertex((iLine.VerticesCount) - 1)
            Segment(1) = iLine.Vertex(iLine.VerticesCount)
        Else
            i = i + 1
            If Dist_Segment_to_Point(iLine.Vertex(i), iLine.Vertex(i + 1), iPoint) >= Dist_Segment_to_Point(iLine.Vertex(i - 1), iLine.Vertex(i), iPoint) Then
                Segment(0) = iLine.Vertex(i - 1)
                Segment(1) = iLine.Vertex(i)
            Else
                Segment(0) = iLine.Vertex(i)
                Segment(1) = iLine.Vertex(i + 1)
            End If
        End If
    GetClosestSegment3d = Segment
End Function

Private Sub GetParamFromObj(mAxis As LineElement, mElement As Element, ByRef Area As Double)
    Dim mVertex() As Point3d
    Dim mStation As Double
    Dim i As Long
    
    
    GetVertexis mElement, mVertex, Area
    
    If UBound(mVertex) >= 0 Then
        
        startStation = GetStation(mAxis, mVertex(0))
        endStation = GetStation(mAxis, mVertex(0))
        endPoint.station = endStation
        endPoint.origin = mVertex(0)
        stPoint.station = endStation
        stPoint.origin = mVertex(0)
        For i = 0 To UBound(mVertex)
            mStation = GetStation(mAxis, mVertex(i))
            If mStation > endStation Then
                endStation = mStation
                endPoint.station = mStation
                endPoint.origin = mVertex(i)
            End If
            If mStation < startStation Then
                startStation = mStation
                stPoint.station = mStation
                stPoint.origin = mVertex(i)
            End If
        Next i
    End If
End Sub
Private Function GetStation(mAxis As LineElement, mPoint As Point3d) As Double
    Dim prPoint As Point3d
    
    'prPoint = Project_Point1(mAxis, mPoint)
    GetStation = mAxis.AsLineElement.DistanceAtPoint(mPoint)
    
End Function

Private Sub DrawOffset(mAxis As LineElement, mPoint As Point3d, ByRef prPoint As Point3d)
    
    Dim perpend As LineElement
    
    prPoint = Project_Point1(mAxis, mPoint)
    
    Set perpend = CreateLineElement2(Nothing, mPoint, prPoint)
    
    perpend.Level = CheckLevel(UserForm1.TextBox_Level_Mark.Text)
    ActiveModelReference.AddElement perpend
    perpend.Redraw
    
End Sub
Private Sub GetVertexis(myElement As Element, mVertx() As Point3d, ByRef mArea As Double) ' Массив вертексов из элемента
    Select Case myElement.Type
        Case msdElementTypeShape
            mVertx = myElement.AsShapeElement.GetVertices
            mArea = myElement.AsShapeElement.Area
        Case msdElementTypeCellHeader
            ReDim mVertx(0)
            mVertx(0) = myElement.AsCellElement.origin
        Case msdElementTypeSharedCell
            ReDim mVertx(0)
            mVertx(0) = myElement.AsCellElement.origin
        Case msdElementTypeLine
            If Point3dEqual(myElement.AsLineElement.startPoint, myElement.AsLineElement.endPoint) Then
                ReDim mVertx(0)
                mVertx(0) = myElement.AsLineElement.startPoint
            Else
                ReDim mVertx(1)
                mVertx(0) = myElement.AsLineElement.startPoint
                mVertx(1) = myElement.AsLineElement.endPoint
                mArea = myElement.AsLineElement.Length
            End If
        Case msdElementTypeLineString
            mVertx = myElement.AsLineElement.GetVertices
            mArea = myElement.AsLineElement.Length
    End Select
End Sub

Function AngleTxt(pSt As Point3d, pEnd As Point3d) As Double
Dim dAng As Double
Dim Angle As Double
Dim ang As Double
Dim dx As Double
Dim dy As Double
dx = pEnd.X - pSt.X
dy = pEnd.Y - pSt.Y
If dy <> 0 Then
    ang = Atn(dx / dy)
    If dx >= 0 And dy > 0 Then
        dAng = ang
    ElseIf dx >= 0 And dy < 0 Then
        dAng = ang + Pi
    ElseIf dx < 0 And dy < 0 Then
        dAng = ang + Pi
    ElseIf dx < 0 And dy > 0 Then
        dAng = ang + 2 * Pi
    End If
ElseIf dy = 0 Then

    If dx > 0 Then
        dAng = Pi / 2
    ElseIf dx < 0 Then
        dAng = 3 * Pi / 4
    End If
End If
Angle = Pi / 2 - dAng

'************* Убрать кавычки для того, что бы автоматом разворачивались подписи
'--------------------------------------------------------------------------
'    If MyForm.CheckBox_rotation.Value = True Then
'        If Angle > Pi * 0.5 And Angle < Pi * 1.5 Then Angle = Angle + Pi
'        If Angle > -Pi * 1.5 And Angle < -Pi * 0.5 Then Angle = Angle + Pi
'    End If
AngleTxt = Angle

End Function

Attribute VB_Name = "Module1"
Option Explicit
Public Type pointVertex
    origin As Point3d
    station As Double
    
End Type

Sub main()
    UserForm1.Show vbModeless
End Sub

Attribute VB_Name = "UserForm1"
Attribute VB_Base = "0{B7F261B3-62AF-4380-8E3C-8E2C318CD39B}{89B6D458-2A0D-4B58-8234-2E3E42B1AB2E}"
Attribute VB_GlobalNameSpace = False
Attribute VB_Creatable = False
Attribute VB_PredeclaredId = True
Attribute VB_Exposed = False
Attribute VB_TemplateDerived = False
Attribute VB_Customizable = False
Private Sub ComboBox_level_of_obj_DblClick(ByVal Cancel As MSForms.ReturnBoolean)
    InitializeLevels ComboBox_level_of_obj
End Sub

Private Sub CommandButton_Delet_markers_Click()
    DeleteMarkers UserForm1.TextBox_Level_Mark.Text
End Sub

Private Sub CommandButton_detect_axis_Click()
    CommandState.StartLocate New LCE_Line_Snap
End Sub

Private Sub InitializeLevels(mComboBox As ComboBox)
    Dim MyLevel As Level
    
    mComboBox.Clear
    For Each MyLevel In ActiveDesignFile.Levels
        mComboBox.AddItem MyLevel.Name
    Next
End Sub
Private Sub UserForm_Initialize()
    InitializeLevels ComboBox_level_of_obj
    InitializeLevels ComboBox_LevelBuffer
End Sub

Private Sub DeleteMarkers(slevel As String)
    Dim mEnum As ElementEnumerator
    Dim mFilter As New ElementScanCriteria
    Dim mLevel As Level
        
    On Error Resume Next
    Set mLevel = ActiveDesignFile.Levels(slevel)
    If Err.Number = 5 Or Err.Number = -2147024809 Then
        Err.Clear
        Exit Sub
    End If
    mFilter.ExcludeAllLevels
    mFilter.IncludeLevel mLevel
    
    Set mEnum = ActiveModelReference.Scan(mFilter)
    
    While mEnum.MoveNext
        ActiveModelReference.RemoveElement mEnum.Current
        mEnum.Current.Redraw
    Wend
    ActiveDesignFile.DeleteLevel mLevel
    ActiveDesignFile.Levels.Rewrite
End Sub
