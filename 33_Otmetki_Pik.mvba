Attribute VB_Name = "Module1"
Option Explicit
Sub main()
    UserForm1.Show vbModeless
    
End Sub

Attribute VB_Name = "UserForm1"
Attribute VB_Base = "0{2A05C786-D3FB-4DA8-8314-97D306168E9F}{4EBC1FF8-D4B3-42A6-8499-95F05222DE61}"
Attribute VB_GlobalNameSpace = False
Attribute VB_Creatable = False
Attribute VB_PredeclaredId = True
Attribute VB_Exposed = False
Attribute VB_TemplateDerived = False
Attribute VB_Customizable = False
Option Explicit
Private Sub ComboBox_pointLevel_DblClick(ByVal Cancel As MSForms.ReturnBoolean)
    IniLevel
End Sub

Private Sub CommandButton_berg_Click()
    Bergshtrih
End Sub

Private Sub CommandButton_Del_Pik_Click()
    DelPIk
End Sub

Private Sub CommandButton_L2S_Click()
    LineStringToShape
End Sub

Private Sub CommandButton1_Click()
    CreatePoint
End Sub

Private Sub UserForm_Initialize()
    inizializeLevels
    IniLevel
End Sub
Private Sub IniLevel()
    Dim MyModel As ModelReference
    Dim myLevel As Level
    ComboBox_pointLevel.Clear
    Set MyModel = ActiveDesignFile.DefaultModelReference
        For Each myLevel In MyModel.Levels
            ComboBox_pointLevel.AddItem myLevel.Name
        Next
End Sub
Private Sub inizializeLevels()
    Dim myLevel As Level
    Dim MyLevelName() As String
    ReDim MyLevelName(0)
    Dim MadeChange As Boolean
    Dim I As Integer
    Dim tmpName As String
        MyListBox.Clear
    For Each myLevel In ActiveDesignFile.Levels
        MyLevelName(UBound(MyLevelName)) = myLevel.Name
        ReDim Preserve MyLevelName(UBound(MyLevelName) + 1)
    Next
        ReDim Preserve MyLevelName(UBound(MyLevelName) - 1)
        
        MadeChange = True
        While MadeChange = True
            MadeChange = False
            For I = LBound(MyLevelName) To UBound(MyLevelName) - 1
                If StrComp(MyLevelName(I), MyLevelName(I + 1)) = 1 Then
                    tmpName = MyLevelName(I)
                    MyLevelName(I) = MyLevelName(I + 1)
                    MyLevelName(I + 1) = tmpName
                    MadeChange = True
                End If
            Next I
        Wend
        For I = LBound(MyLevelName) To UBound(MyLevelName)
            MyListBox.AddItem MyLevelName(I)
        Next I
End Sub

Private Sub CreatePoint()
    Dim MyEnum As ElementEnumerator
    Dim myFilter As New ElementScanCriteria
    Dim k As Integer
    Dim I As Long ' Счетчик контуров
    Dim j As Long
    Dim hit As Boolean
    Dim myShape() As Element
    
    
    myFilter.ExcludeAllTypes
    myFilter.IncludeType msdElementTypeShape
  
    myFilter.ExcludeAllLevels
    
        For k = 1 To UserForm1.MyListBox.ListCount
            If UserForm1.MyListBox.Selected(k - 1) Then
                myFilter.IncludeLevel ActiveDesignFile.Levels.Find(UserForm1.MyListBox.List(k - 1))
            End If
        Next k
    Set MyEnum = ActiveModelReference.Scan(myFilter)
    myShape() = MyEnum.BuildArrayFromContents
    For I = 0 To UBound(myShape)
        hit = False
            For j = 0 To UBound(myShape)
                If I <> j Then
                    If Point3dInPolygonXY(myShape(j).AsShapeElement.Vertex(1), myShape(I).AsShapeElement.GetVertices) = 1 Then
                        hit = True
                    End If
                End If
            Next j
            If hit = False Then
                    myShape(I).Color = CInt(UserForm1.TextBox_color)
                    myShape(I).Rewrite
                    myShape(I).Redraw
            End If
    Next I

End Sub
Private Sub DelPIk()
    Dim MyEnum As ElementEnumerator
    Dim myFilter As New ElementScanCriteria
    Dim I As Long ' Счетчик контуров
    Dim k As Long
    Dim d As Long
    Dim a As Double
    Dim myShape() As Element
    
    myFilter.ExcludeAllTypes
    myFilter.IncludeType msdElementTypeShape
  
    myFilter.ExcludeAllLevels
    d = 0
    
        For k = 1 To UserForm1.MyListBox.ListCount
            If UserForm1.MyListBox.Selected(k - 1) Then
                myFilter.IncludeLevel ActiveDesignFile.Levels.Find(UserForm1.MyListBox.List(k - 1))
            End If
        Next k
        
    Set MyEnum = ActiveModelReference.Scan(myFilter)
    
    Do While MyEnum.MoveNext
        On Error GoTo ErrorHandler
        a = MyEnum.Current.AsClosedElement.Area
        If a < CDbl(UserForm1.TextBox1.Text) Then
            ActiveModelReference.RemoveElement MyEnum.Current
            MyEnum.Current.Redraw
            d = d + 1
        End If
ErrorHandler:
    Loop
    MsgBox "Удалено" & d & "piks"
End Sub
Private Sub LineStringToShape()
    Dim MyEnum As ElementEnumerator
    Dim myFilter As New ElementScanCriteria
    Dim I As Long ' Счетчик контуров
    Dim k As Long
    Dim d As Long
    Dim a As Double
    Dim myShape() As Element
    Dim mShape As ShapeElement
    
    
    myFilter.ExcludeAllTypes
    myFilter.IncludeType msdElementTypeLineString
  
    myFilter.ExcludeAllLevels
    
    d = 0
    
        For k = 1 To UserForm1.MyListBox.ListCount
            If UserForm1.MyListBox.Selected(k - 1) Then
                myFilter.IncludeLevel ActiveDesignFile.Levels.Find(UserForm1.MyListBox.List(k - 1))
            End If
        Next k
        
    Set MyEnum = ActiveModelReference.Scan(myFilter)
    
    Do While MyEnum.MoveNext
        On Error GoTo ErrorHandler
            If Point3dEqual(MyEnum.Current.AsLineElement.StartPoint, MyEnum.Current.AsLineElement.EndPoint) Then
                Set mShape = CreateShapeElement1(MyEnum.Current, MyEnum.Current.AsLineElement.AsVertexList.GetVertices, msdFillModeNotFilled)
                ActiveModelReference.RemoveElement MyEnum.Current
                MyEnum.Current.Redraw
                ActiveModelReference.AddElement mShape
                mShape.Redraw
                d = d + 1
        End If
ErrorHandler:

    Loop
'    For I = 0 To UBound(myShape)
'        If myShape(I).AsShapeElement.Area < CDbl(UserForm1.TextBox1.Text) Then
'            ActiveModelReference.RemoveElement myShape(I)
'            myShape(I).Rewrite
'            myShape(I).Redraw
'            d = d + 1
'        End If
'    Next I
    MsgBox "Заменено " & d & " piks"
End Sub

Sub createCentroid(tShape As ShapeElement)
    Dim Centr As Point3d
    Dim mPoint As LineElement
    
'    Centr = tShape.Centroid
'
'    Set mPoint = CreateLineElement2(Nothing, Centr, Centr)
'    ActiveModelReference.AddElement mPoint
    mPoint.LineWeight = 5
    mPoint.Rewrite
    mPoint.Redraw
End Sub

Private Sub Bergshtrih()
    Dim MyEnum As ElementEnumerator
    Dim myFilter As New ElementScanCriteria
    Dim k As Integer
    Dim myShape() As Element
    Dim myPoint() As Element
    Dim MyEnumPoint As ElementEnumerator
    Dim myFilterPoint As New ElementScanCriteria
    Dim I As Long
    Dim j As Long
    
    myFilter.ExcludeAllTypes
    myFilter.ExcludeAllColors
    myFilter.IncludeColor (CInt(UserForm1.TextBox_color))
    myFilter.IncludeType msdElementTypeShape
    myFilter.ExcludeAllLevels
        For k = 1 To UserForm1.MyListBox.ListCount
            If UserForm1.MyListBox.Selected(k - 1) Then
                myFilter.IncludeLevel ActiveDesignFile.Levels.Find(UserForm1.MyListBox.List(k - 1))
            End If
        Next k
    Set MyEnum = ActiveModelReference.Scan(myFilter)
    myShape() = MyEnum.BuildArrayFromContents
    
    myFilterPoint.ExcludeAllTypes
'   myFilterPoint.IncludeType msdElementTypeCellHeader
    myFilterPoint.IncludeType msdElementTypeLine
    myFilterPoint.ExcludeAllLevels
    
    myFilterPoint.IncludeLevel ActiveDesignFile.Levels.Find(UserForm1.ComboBox_pointLevel.Text)
    Set MyEnumPoint = ActiveModelReference.Scan(myFilterPoint)
    myPoint() = MyEnumPoint.BuildArrayFromContents
   
    For I = 0 To UBound(myShape)
        For j = 0 To UBound(myPoint)
            If Point3dInPolygonXY(myPoint(j).AsLineElement.StartPoint, myShape(I).AsShapeElement.GetVertices) = 1 Then
                DetectPik myPoint(j).AsLineElement.StartPoint, myShape(I).AsShapeElement
            End If
        Next j
    Next I
End Sub

Private Sub DetectPik(mPoint As Point3d, mShape As ShapeElement)
    Dim pik As Integer '1 - pik ; -1 - pit
    Dim maxL As Double
    Dim l As Double
    Dim ll As Double ' допуск для второго бергштриха
    Dim mP As Point3d
    Dim I As Long
    Dim Id As Long
    Dim IdG As Long
    Dim mLevel As String
    pik = 1
    If mPoint.Z > mShape.Vertex(1).Z Then
        pik = -1
    End If
        mLevel = mShape.Level.Name
        maxL = Point3dDistanceXY(mPoint, mShape.Vertex(1))
        Id = 1
        For I = 2 To mShape.VerticesCount - 1
            l = Point3dDistanceXY(mPoint, mShape.Vertex(I))
            If l > maxL Then
                maxL = l
                Id = I
            End If
        Next I
        DrawBerg mShape, Id, pik, mLevel
        IdG = Id
        
        maxL = 0
        ll = Point3dDistanceXY(mPoint, mShape.Vertex(Id))
        For I = 1 To mShape.VerticesCount - 1
            l = Point3dDistanceXY(mPoint, mShape.Vertex(I))
            If l > maxL Then
                If ll < Point3dDistanceXY(mShape.Vertex(IdG), mShape.Vertex(I)) Then
                    maxL = l
                    Id = I
                End If
            End If
        Next I
        
        DrawBerg mShape, Id, pik, mLevel
End Sub

Private Sub DrawBerg(mShape As ShapeElement, Id As Long, pik As Integer, mLevel As String)

    Dim v1 As Vector3d
    Dim v2 As Vector3d
    Dim v3 As Vector3d
    Dim berg As LineElement
    
        v1 = Vector3dSubtractPoint3dPoint3d(mShape.Vertex(Id + 1), mShape.Vertex(Id))
        If Id = 1 Then
            v2 = Vector3dSubtractPoint3dPoint3d(mShape.Vertex(mShape.VerticesCount - 1), mShape.Vertex(Id))
        Else
            v2 = Vector3dSubtractPoint3dPoint3d(mShape.Vertex(Id - 1), mShape.Vertex(Id))
        End If
        
        v3 = Vector3dAdd(Vector3dScale(v1, 1 / Vector3dMagnitude(v1)), Vector3dScale(v2, 1 / Vector3dMagnitude(v2)))
        Set berg = CreateLineElement2(Nothing, mShape.Vertex(Id), Point3dAddPoint3dVector3d(mShape.Vertex(Id), Vector3dScale(v3, pik * CDbl(TextBox_len) * 1 / Vector3dMagnitude(v3))))
        berg.Level = ActiveModelReference.Levels.Find(mLevel)
        berg.LineStyle = ActiveDesignFile.LineStyles("0")
        ActiveModelReference.AddElement berg
        berg.Redraw
    
End Sub
