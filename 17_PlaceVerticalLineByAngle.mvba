Attribute VB_Name = "FnScan"

Option Explicit

' ???????? ??? ???????? ??????????
Declare Function mdlSystem_findMdlDesc Lib "stdmdlbltin.dll" (ByVal nameP As String) As Long
Declare Function mdlSystem_loadMdlProgram Lib "stdmdlbltin.dll" (ByVal pathP As String, ByVal Taskidp As String, ByVal pArgument As String) As Long

' ??????????????????? ??????? ?????? ? ??????? (????????? ???????? ???????? ?????????? ?? ?????????)
    Private Declare Sub CopyMemoryToVBA Lib "kernel32" Alias "RtlMoveMemory" (ByRef VBALocation As Any, ByVal SourceLoc As Long, ByVal Length As Long)
    Private Declare Sub CopyMemoryFromVBA Lib "kernel32" Alias "RtlMoveMemory" (ByVal Destination As Long, ByRef VBALocation As Any, ByVal Length As Long)
    Private Declare Sub MoveMemory Lib "kernel32" Alias "RtlMoveMemory" (ByVal strDest As Any, ByVal lpSource As Any, ByVal Length As Long)

' ??? ????? ? ?????????????? ????????????
    Type Point3dLong
        x As Long
        y As Long
        Z As Long
    End Type

' ??? ?????
    Type RGB
        r As Byte
        G As Byte
        B As Byte
    End Type
     
' ???? ??????????, ??????? ?????????? ????? ??? ?????? ? ???????
' Point3d Pnt ;         // Coordinates
' BYTE Code ;       // Classification code
' BYTE Echo ;       // Echo information
' BYTE Flag ;       // Runtime flag (view visibility)
' BYTE Mark ;       // Runtime flag
' USHORT Line ;         // Flightline number
' USHORT Intensity ; // Intensity value

' Point3d - ??? X, Y, Z (?????? Long, ?.?. 4 ?????)
' Byte ? C/C++ ????????? ? Byte ? VBA (1 ????)
' USHORT ? C/C++ ?? ????? ??????? ? VBA, ????? 2 ?????, ??? ???????? ????? ???????????? Long (0 - 65535)
' Double ? C/C++ ????????? ? Double ? VBA (8 ????)

' ??????? FnScanGet ????????? ?????????? ????? ? ????? ?????????? ???????? ??? ?????? ?????
' ??? ????????? ???????? ????? ???????????? ????? ?????:
' CopyMemoryToVBA Value, Tbl, 4
' Value - ?????????? ???? ????, ??????? ????? (Byte, Long, Double)
' Tbl - ????????? (?????) ??? ????????? ??????????
' 4 - ?????? ? ??????, ??????? ?????????? ? ???????? ???????? (??. ???? ???????? ???????? ??????????)
' ?.?. ?????? FnScanGet ?????????? ?????????? ?????, ?? ????? ???????? ???? ?????? ????????
' ????????:
            ' 1. ??? ????????? ???????? ????????????? ????????? ?????: CopyMemoryToVBA Ints, Tbl + 2 * (Exp - 1), 2
            ' 2. ??? ????????? ???????? ????? (R) ????????? ?????: CopyMemoryToVBA Clr, Tbl + 1 * (Exp - 1) * 3, 1
            ' 3. ??? ????????? ???????? ????? (B) ????????? ?????: CopyMemoryToVBA Clr, Tbl + 1 * (Exp - 1) * 3 + 2, 1

'Attribute                      Always      C Data              Type Size
'Point coordinates              Yes         Point3d             12 bytes
'Time stamps                    -           double              8 bytes
'Group identifiers              -           unsigned int        4 bytes
'Normal vectors                 -           unsigned int        4 bytes
'Distances                      -           int                 4 bytes
'RGB colors                     -           RgbClr              3 bytes
'Intensity values               -           unsigned short      2 bytes
'Line numbers                   -           unsigned short      2 bytes
'Echo lengths                   -           short               2 bytes
'Parameter values               -           unsigned short      2 bytes
'Point classes                  Yes         unsigned char       1 byte
'Mark values -- run time only   Yes         unsigned char       1 byte
'Flag values -- run time only   Yes         unsigned char       1 byte
'Scanner angles                 -           char                1 byte
'Echo bits                      -           unsigned char       1 byte
'Scanner numbers                -           unsigned char       1 byte
'Echo normality values          -           unsigned char       1 byte

' ????????? ????????? ?? ??????????
Sub LoadApp(Appname)
    Dim Ldd As Long
    If mdlSystem_findMdlDesc(Appname) = 0 Then
        Ldd = mdlSystem_loadMdlProgram(Appname, "Null", "")
    End If
End Sub

' ?????????? ?????, ?????????? Point3d (?????? TerraSolid)
Function FnScanGetPnt(ByRef Tbl As Long) As Long
    FnScanGetPnt = GetCExpressionValue("FnScanGetPnt(" & VarPtr(Tbl) & ")")
End Function

Function FnScanGetCls(ByRef Tbl As Long) As Long
    FnScanGetCls = GetCExpressionValue("FnScanGetCls(" & VarPtr(Tbl) & ")")
End Function

Function FnScanGetMrk(ByRef Tbl As Long) As Long
    FnScanGetMrk = GetCExpressionValue("FnScanGetMrk(" & VarPtr(Tbl) & ")")
End Function

Function FnScanGetFlg(ByRef Tbl As Long) As Long
    FnScanGetFlg = GetCExpressionValue("FnScanGetFlg(" & VarPtr(Tbl) & ")")
End Function

Function FnScanGetInt(ByRef Tbl As Long) As Long
    FnScanGetInt = GetCExpressionValue("FnScanGetInt(" & VarPtr(Tbl) & ")")
End Function

Function FnScanGetLin(ByRef Tbl As Long) As Long
    FnScanGetLin = GetCExpressionValue("FnScanGetLin(" & VarPtr(Tbl) & ")")
End Function

Function FnScanGetDbl(ByRef Tbl As Long) As Long
    FnScanGetDbl = GetCExpressionValue("FnScanGetDbl(" & VarPtr(Tbl) & ")")
End Function

Function FnScanGetEch(ByRef Tbl As Long) As Long
    FnScanGetEch = GetCExpressionValue("FnScanGetEch(" & VarPtr(Tbl) & ")")
End Function

Function FnScanGetAng(ByRef Tbl As Long) As Long
    FnScanGetAng = GetCExpressionValue("FnScanGetAng(" & VarPtr(Tbl) & ")")
End Function

Function FnScanGetClr(ByRef Tbl As Long) As Long
    FnScanGetClr = GetCExpressionValue("FnScanGetClr(" & VarPtr(Tbl) & ")")
End Function

Function FnScanGetScr(ByRef Tbl As Long) As Long
    FnScanGetScr = GetCExpressionValue("FnScanGetScr(" & VarPtr(Tbl) & ")")
End Function

Function FnScanGetCoordSetup(ByRef Org As Point3d) As Long
    FnScanGetCoordSetup = GetCExpressionValue("FnScanGetCoordSetup(" & VarPtr(Org) & ")")
End Function

' ??????? ??? ????????? ??????? ????? ? ?????????? ??????????? ? ???????????? ? ??????????? ????????? ?????
Function FnScanGetPntArray(ByRef Tbl() As Point3d) As Long
    Dim First As Long
    FnScanGetPntArray = FnScanGetPnt(First)
    
    If FnScanGetPntArray > 0 Then
        Dim i As Long, UorPerMast As Long
        Dim Org As Point3d
        Dim Mul As Double
        Dim PCoL() As Point3dLong
        UorPerMast = FnScanGetCoordSetup(Org)
        Mul = 1 / UorPerMast
        
        ReDim Preserve Tbl(FnScanGetPntArray - 1)
        ReDim Preserve PCoL(FnScanGetPntArray - 1)
        CopyMemoryToVBA PCoL(0), First, FnScanGetPntArray * 12
        
        For i = LBound(PCoL) To UBound(PCoL)
            Tbl(i).x = Org.x + (Mul * PCoL(i).x)
            Tbl(i).y = Org.y + (Mul * PCoL(i).y)
            Tbl(i).Z = Org.Z + (Mul * PCoL(i).Z)
        Next i
    End If
End Function

' ??????? ????????? ??????? ???? ??????????? ?????
Function FnScanGetClsArray(ByRef Tbl() As Byte) As Long
    Dim First As Long
    FnScanGetClsArray = FnScanGetCls(First)
    
    If FnScanGetClsArray = 0 Then
        Exit Function
    End If
    
    ReDim Preserve Tbl(FnScanGetClsArray - 1)
    CopyMemoryToVBA Tbl(0), First, FnScanGetClsArray
End Function

' ??????? ????????? ???????? Mark ???? ??????????? ?????
Function FnScanGetMrkArray(ByRef Tbl() As Byte) As Long
    Dim First As Long
    FnScanGetMrkArray = FnScanGetMrk(First)
    
    If FnScanGetMrkArray = 0 Then
        Exit Function
    End If
    
    ReDim Preserve Tbl(FnScanGetMrkArray - 1)
    CopyMemoryToVBA Tbl(0), First, FnScanGetMrkArray
End Function

' ??????? ????????? ???????? Flag ???? ??????????? ?????
Function FnScanGetFlgArray(ByRef Tbl() As Byte) As Long
    Dim First As Long
    FnScanGetFlgArray = FnScanGetFlg(First)
    
    If FnScanGetFlgArray = 0 Then
        Exit Function
    End If
    
    ReDim Preserve Tbl(FnScanGetFlgArray - 1)
    CopyMemoryToVBA Tbl(0), First, FnScanGetFlgArray
End Function

' ??????? ????????? ????????????? ???? ??????????? ?????
' ??-?? ??????????? ????? ?????? VBA ?? ?????? ??? ????????????? ????????? 65536 ? ???????? ?????????????
Function FnScanGetIntArray(ByRef Tbl() As Long) As Long
    Dim First As Long, i As Long
    Dim Prelim() As Integer
    FnScanGetIntArray = FnScanGetInt(First)
    
    If FnScanGetIntArray = 0 Then
        Exit Function
    End If
    
    ReDim Preserve Tbl(FnScanGetIntArray - 1)
    ReDim Preserve Prelim(FnScanGetIntArray - 1)
    CopyMemoryToVBA Prelim(0), First, FnScanGetIntArray * 2
    
    For i = LBound(Prelim) To UBound(Prelim)
        If Prelim(i) >= 0 Then
            Tbl(i) = Prelim(i)
        Else
            Tbl(i) = Prelim(i) + 65536
        End If
    Next i
End Function

' ??????? ????????? ????????? ???? ??????????? ?????
' ??-?? ??????????? ????? ?????? VBA ?? ?????? ??? ????????????? ????????? 65536 ? ???????? ?????????
Function FnScanGetLinArray(ByRef Tbl() As Long) As Long
    Dim First As Long, i As Long
    Dim Prelim() As Integer
    FnScanGetLinArray = FnScanGetLin(First)
    
    If FnScanGetLinArray = 0 Then
        Exit Function
    End If
    
    ReDim Preserve Tbl(FnScanGetLinArray - 1)
    ReDim Preserve Prelim(FnScanGetLinArray - 1)
    CopyMemoryToVBA Prelim(0), First, FnScanGetLinArray * 2
    
    For i = LBound(Prelim) To UBound(Prelim)
        If Prelim(i) >= 0 Then
            Tbl(i) = Prelim(i)
        Else
            Tbl(i) = Prelim(i) + 65536
        End If
    Next i
End Function

' ??????? ????????? ????????? ????? ???? ??????????? ?????
Function FnScanGetDblArray(ByRef Tbl() As Double) As Long
    Dim First As Long
    FnScanGetDblArray = FnScanGetDbl(First)
    
    If FnScanGetDblArray = 0 Then
        Exit Function
    End If
    
    ReDim Preserve Tbl(FnScanGetDblArray - 1)
    CopyMemoryToVBA Tbl(0), First, FnScanGetDblArray * 8
End Function

' ??????? ????????? ??? ???? ??????????? ?????
Function FnScanGetEchArray(ByRef Tbl() As Byte) As Long
    Dim First As Long
    FnScanGetEchArray = FnScanGetEch(First)
    
    If FnScanGetEchArray = 0 Then
        Exit Function
    End If
    
    ReDim Preserve Tbl(FnScanGetEchArray - 1)
    CopyMemoryToVBA Tbl(0), First, FnScanGetEchArray
End Function

' ??????? ????????? ????? ???? ??????????? ?????
Function FnScanGetClrArray(ByRef Tbl() As RGB) As Long
    Dim First As Long
    FnScanGetClrArray = FnScanGetEch(First)
    
    If FnScanGetClrArray = 0 Then
        Exit Function
    End If
    
    ReDim Preserve Tbl(FnScanGetClrArray - 1)
    CopyMemoryToVBA Tbl(0), First, FnScanGetClrArray * 3
End Function

' ??????? ????????? ??????? ???? ??????????? ?????
Function FnScanGetScrArray(ByRef Tbl() As Byte) As Long
    Dim First As Long
    FnScanGetScrArray = FnScanGetScr(First)
    
    If FnScanGetScrArray = 0 Then
        Exit Function
    End If
    
    ReDim Preserve Tbl(FnScanGetScrArray - 1)
    CopyMemoryToVBA Tbl(0), First, FnScanGetScrArray
End Function

'????????????? ????? ?? ?????? ? ?????
'FromClass - ???????? ????? ????? (???????? 999 - ??? ??????)
'ToClass - ????? ?????????? (?.?. ? ????? ????? ??????????????????)
'Fence, ???? 0 - ?? ??? ?????, ???? 1, ?? ?????? ?????
'?????????? ?????????? ?????????????????? ????? (0...n)
' ?????? -1 ???? ???? ?? ??????, ?? ??? ???? ???????? ?????? ?????? ?????
' ?????? -3 ???? ????????? ????????
Function FnScanClassifyClass(ByVal FromClass As Long, ByVal ToClass As Long, ByVal Fence As Long) As Long
    FnScanClassifyClass = GetCExpressionValue("FnScanClassifyClass(" & FromClass & "," & ToClass & "," & Fence & ")")
End Function

'????????????? Low Point
'FromClass - ???????? ????? ????? (???????? 999 - ??? ??????)
'ToClass - ????? ?????????? (?.?. ? ????? ????? ??????????????????)
'GrpCnt - ???????????? ?????????? Low Point ? ?????? (?? 1 ?? 99)
'Dz - ??????????? ??????? ?? ?????? ???????????? ?????? ????? (??????????? ? ??????)
'XyDst - ?????? ?????? (??????????? ? ??????)
'Fence, ???? 0 - ?? ??? ?????, ???? 1, ?? ?????? ?????
'?????????? ?????????? ?????????????????? ????? (0...n)
' ?????? -1 ???? ???? ?? ??????, ?? ??? ???? ???????? ?????? ?????? ?????
' ?????? -2 ???? ????????
' ?????? -3 ???? ????????? ????????
Function FnScanClassifyLow(ByVal FromClass As Long, ByVal ToClass As Long, ByVal GrpCnt As Long, ByVal dz As Double, ByVal XyDst As Double, ByVal Fence As Long) As Long
    FnScanClassifyLow = GetCExpressionValue("FnScanClassifyLow(" & FromClass & "," & ToClass & "," & GrpCnt & "," & dz & "," & XyDst & "," & Fence & ")")
End Function


' ????????????? Air Point
' ClsLst - ?????? ???????? ???????, ???????? "1,7-9". ?.?. ???????? ???? ?????? ??????, ??????? ????? ?????????? ???????????? ? ?????? ????????
' ToClass - ????? ?????????? (?.?. ? ????? ????? ??????????????????)
' XyDst - ?????? ?????? (??????????? ? ??????)
' ReqCnt - ??????????? ?????????? ????? ?????? ??????????????, ? ??????? ?????????? ?????
' Lim - ??????????? ??????
' Fence, ???? 0 - ?? ??? ?????, ???? 1, ?? ?????? ?????
' ?????????? ?????????? ?????????????????? ????? (0...n)
' ?????? -1 ???? ???? ?? ??????, ?? ??? ???? ???????? ?????? ?????? ?????
' ?????? -2 ???? ????????
' ?????? -3 ???? ????????? ????????
Function FnScanClassifyAir(ByVal ClsLst As String, ByVal ToClass As Long, ByVal XyDst As Double, ByVal ReqCnt As Long, ByVal Lim As Double, ByVal Fence As Long) As Long
    FnScanClassifyAir = GetCExpressionValue("FnScanClassifyAir(" & StrPtr(StrConv(ClsLst & vbNullChar, vbFromUnicode)) & "," & ToClass & "," & XyDst & "," & ReqCnt & "," & Lim & "," & Fence & ")")
End Function

' ????????????? Isolated Point
' ClsLst - ?????? ???????? ???????, ???????? "1,7-9". ?.?. ???????? ???? ?????? ??????, ??????? ????? ?????????? ???????????? ? ?????? ????????
' ToClass - ????? ?????????? (?.?. ? ????? ????? ??????????????????)
' Dst - ?????? ?????? (??????????? ? ??????)
' LimCnt - ????????????????, ???? ?????? ??? Lim
' Fence, ???? 0 - ?? ??? ?????, ???? 1, ?? ?????? ?????
' ?????????? ?????????? ?????????????????? ????? (0...n)
' ?????? -1 ???? ???? ?? ??????, ?? ??? ???? ???????? ?????? ?????? ?????
' ?????? -2 ???? ????????
' ?????? -3 ???? ????????? ????????
Function FnScanClassifyIsolated(ByVal ClsLst As String, ByVal ToClass As Long, ByVal LimCnt As Long, ByVal dst As Double, ByVal Fence As Long) As Long
    FnScanClassifyIsolated = GetCExpressionValue("FnScanClassifyIsolated(" & StrPtr(StrConv(ClsLst & vbNullChar, vbFromUnicode)) & "," & ToClass & "," & LimCnt & "," & dst & "," & Fence & ")")
End Function

' ????????????? Ground Point
' FromClass - ???????? ????? ????? (???????? 999 - ??? ??????)
' ToClass - ????? ?????????? (?.?. ? ????? ????? ??????????????????)
' InitLow - ????????? ?????: 0 - ??????? ????? ?????, 1 - ?????? ?????
' BldSz - ???????????? ?????? ?????? (? ??????) ???? InitLow = 1
' MaxAng - ???????????? terrain angle (???????)
' IterAng - iteration angle (???????)
' IterDst - iteration distance (?????)
' Reduce - reduce iteration length?
' RedLen - when edge length < RedLen
' Stopp - stop iteration?
' StopLen - when edge length < StopLen
' Fence, ???? 0 - ?? ??? ?????, ???? 1, ?? ?????? ?????
' ?????????? ?????????? ?????????????????? ????? (0...n)
' ?????? -1 ???? ???? ?? ??????, ?? ??? ???? ???????? ?????? ?????? ?????
' ?????? -2 ???? ????????
' ?????? -3 ???? ????????? ????????
Function FnScanClassifyGround(ByVal FromClass As Long, ByVal ToClass As Long, ByVal InitLow As Long, ByVal BldSz As Double, _
                              ByVal MaxAng As Double, ByVal IterAng As Double, ByVal IterDst As Double, ByVal Reduce As Long, _
                              ByVal RedLen As Double, ByVal Stopp As Long, ByVal StopLen As Double, ByVal Fence As Long) As Long
    FnScanClassifyGround = GetCExpressionValue("FnScanClassifyGround(" & FromClass & "," & ToClass & "," & InitLow & "," & BldSz & "," & _
                                                                          MaxAng & "," & IterAng & "," & IterDst & "," & Reduce & "," & _
                                                                          RedLen & "," & Stopp & "," & StopLen & "," & Fence & ")")
End Function

' ????????????? ????? ??? ????????????
' FromClass - ???????? ????? ????? (????? ?????, ?.?. ?????, ??????? ???? ???????????)
' ToClass - ????? ?????????? (?.?. ? ????? ????? ??????????????????)
' Lim - ?????
' Tol - ?????? ?? ??????
' Fence, ???? 0 - ?? ??? ?????, ???? 1, ?? ?????? ?????
' ?????????? ?????????? ?????????????????? ????? (0...n)
' ?????? -1 ???? ???? ?? ??????, ?? ??? ???? ???????? ?????? ?????? ?????
' ?????? -2 ???? ????????
' ?????? -3 ???? ????????? ????????
Function FnScanClassifyBelow(ByVal FromClass As Long, ByVal ToClass As Long, ByVal Lim As Double, ByVal TolZ As Double, ByVal Fence As Long) As Long
    FnScanClassifyBelow = GetCExpressionValue("FnScanClassifyBelow(" & FromClass & "," & ToClass & "," & Lim & "," & TolZ & "," & Fence & ")")
End Function

' ????????????? ????? ??? ??????
' Grd - ????? ????? ??? 1000000 + TerraModeler surface id
' MaxLen -  maximum ground triangle length
' FromClass - source class (999 for any)
' ToClass - destination class
' MinH - minimum height above ground
' MaxH - maximum height above ground
' Fence, ???? 0 - ?? ??? ?????, ???? 1, ?? ?????? ?????
' ?????????? ?????????? ?????????????????? ????? (0...n)
' ?????? -1 ???? ???? ?? ??????, ?? ??? ???? ???????? ?????? ?????? ?????
' ?????? -2 ???? ????????
' ?????? -3 ???? ????????? ????????
Function FnScanClassifyHgtGrd(ByVal Grd As Long, ByVal MaxLen As Double, ByVal FromClass As Long, ByVal ToClass As Long, _
                              ByVal MinH As Double, ByVal MaxH As Double, ByVal Fence As Long) As Long
    FnScanClassifyHgtGrd = GetCExpressionValue("FnScanClassifyHgtGrd(" & Grd & "," & MaxLen & "," & FromClass & "," & ToClass & "," & MinH & "," & MaxH & "," & Fence & ")")
End Function


' ????????????? ????? ???????????? ?????????? ???????
' ?????????? FnScanClassifyHgtGrd, ?? ?????? ByVal Grd As Long ?????????? ByVal GrdLst As String
' GrdLst list of ground classes, example "2,8"
Function FnScanClassifyHgtLst(ByVal GrdLst As String, ByVal MaxLen As Double, ByVal FromClass As Long, ByVal ToClass As Long, _
                              ByVal MinH As Double, ByVal MaxH As Double, ByVal Fence As Long) As Long
    FnScanClassifyHgtLst = GetCExpressionValue("FnScanClassifyHgtLst(" & StrPtr(StrConv(GrdLst & vbNullChar, vbFromUnicode)) & "," & MaxLen & "," & FromClass & "," & ToClass & "," & MinH & "," & MaxH & "," & Fence & ")")
End Function


' ????????????? ????? ? ???????????? ????????? ????? MinZ <= Z < MaxZ
' FromClass - ???????? ????? ????? (???????? 999 - ??? ??????)
' ToClass - ????? ?????????? (?.?. ? ????? ????? ??????????????????)
' MinZ - ??????????? ??????
' MaxZ - ???????????? ??????
' Fence, ???? 0 - ?? ??? ?????, ???? 1, ?? ?????? ?????
' ?????????? ?????????? ?????????????????? ????? (0...n)
' ?????? -1 ???? ???? ?? ??????, ?? ??? ???? ???????? ?????? ?????? ?????
' ?????? -2 ???? ????????
' ?????? -3 ???? ????????? ????????
Function FnScanClassifyAbsElev(ByVal FromClass As Long, ByVal ToClass As Long, ByVal MinZ As Double, ByVal MaxZ As Double, ByVal Fence As Long) As Long
    FnScanClassifyAbsElev = GetCExpressionValue("FnScanClassifyAbsElev(" & FromClass & "," & ToClass & "," & MinZ & "," & MaxZ & "," & Fence & ")")
End Function


' ????????????? ????? ? ???????????? ????????? ????????????? MinV <= Intensity < MaxV
' FromClass - ???????? ????? ????? (???????? 999 - ??? ??????)
' ToClass - ????? ?????????? (?.?. ? ????? ????? ??????????????????)
' MinZ - ??????????? ?????????????
' MaxZ - ???????????? ?????????????
' Fence, ???? 0 - ?? ??? ?????, ???? 1, ?? ?????? ?????
' ?????????? ?????????? ?????????????????? ????? (0...n)
' ?????? -1 ???? ???? ?? ??????, ?? ??? ???? ???????? ?????? ?????? ?????
' ?????? -2 ???? ????????
' ?????? -3 ???? ????????? ????????
Function FnScanClassifyIntensity(ByVal FromClass As Long, ByVal ToClass As Long, ByVal MinV As Double, ByVal MaxV As Double, ByVal Fence As Long) As Long
    FnScanClassifyIntensity = GetCExpressionValue("FnScanClassifyIntensity(" & FromClass & "," & ToClass & "," & MinV & "," & MaxV & "," & Fence & ")")
End Function

' ????????????? ????? ? ???????????? ????????? ?????? ? ?????????????? ???????? ?????? HSV
' FromClass - ???????? ????? ????? (???????? 999 - ??? ??????)
' ToClass - ????? ?????????? (?.?. ? ????? ????? ??????????????????)
' Source color source: 0=laser, 1=ortho, 2=raw images
' Foot laser footprint diameter (m) in ortho/raw images
' Hue hue value
' Tol +- tolerance for hue
' SatMin minimum saturation
' SatMax maximum saturation
' ValMin minimum value
' ValMax maximum value
' Fence, ???? 0 - ?? ??? ?????, ???? 1, ?? ?????? ?????
' ?????????? ?????????? ?????????????????? ????? (0...n)
' ?????? -1 ???? ???? ?? ??????, ?? ??? ???? ???????? ?????? ?????? ?????
' ?????? -2 ???? ????????
' ?????? -3 ???? ????????? ????????
Function FnScanClassifyColor(ByVal FromClass As Long, ByVal ToClass As Long, ByVal Source As Long, ByVal Foot As Double, ByVal Hue As Long, _
                             ByVal Tol As Long, ByVal SatMin As Long, ByVal SatMax As Long, ByVal ValMin As Long, ByVal ValMax As Long, ByVal Fence As Long) As Long
    FnScanClassifyColor = GetCExpressionValue("FnScanClassifyColor(" & FromClass & "," & ToClass & "," & Source & "," & Foot & "," & Hue & "," & _
                                                                       Tol & "," & SatMin & "," & SatMax & "," & ValMin & "," & ValMax & "," & Fence & ")")
End Function


' ????????????? ????? ? ???????????? ????????? ??????? Beg <= Time <= End
' FromClass - ???????? ????? ????? (???????? 999 - ??? ??????)
' ToClass - ????? ?????????? (?.?. ? ????? ????? ??????????????????)
' BegTime - ????????? ????? (???????)
' EndTime - ???????? ????? (???????)
' Fence, ???? 0 - ?? ??? ?????, ???? 1, ?? ?????? ?????
' ?????????? ?????????? ?????????????????? ????? (0...n)
' ?????? -1 ???? ???? ?? ??????, ?? ??? ???? ???????? ?????? ?????? ?????
' ?????? -2 ???? ????????
' ?????? -3 ???? ????????? ????????
Function FnScanClassifyTime(ByVal FromClass As Long, ByVal ToClass As Long, ByVal BegTime As Double, ByVal EndTime As Double, ByVal Fence As Long) As Long
    FnScanClassifyTime = GetCExpressionValue("FnScanClassifyTime(" & FromClass & "," & ToClass & "," & BegTime & "," & EndTime & "," & Fence & ")")
End Function

' Classify model keypoints which produce a triangulated surface model of given accuracy.
' ClsLst - ???????? ????? ?????, example "2,14"
' ToClass - ????? ?????????? (?.?. ? ????? ????? ??????????????????)
' InitDst - initial sampling distance (m)
' Above - distance points may be above model (m)
' Below - distance points may be below model (m)
' Fence, ???? 0 - ?? ??? ?????, ???? 1, ?? ?????? ?????
' ?????????? ?????????? ?????????????????? ????? (0...n)
' ?????? -1 ???? ???? ?? ??????, ?? ??? ???? ???????? ?????? ?????? ?????
' ?????? -2 ???? ????????
' ?????? -3 ???? ????????? ????????
Function FnScanClassifyModelKey(ByVal ClsLst As String, ByVal ToClass As Long, ByVal InitDst As Double, ByVal Above As Double, ByVal Below As Double, ByVal Fence As Long) As Long
    FnScanClassifyModelKey = GetCExpressionValue("FnScanClassifyModelKey(" & StrPtr(StrConv(ClsLst & vbNullChar, vbFromUnicode)) & "," & ToClass & "," & InitDst & "," & Above & "," & Below & "," & Fence & ")")
End Function

' Classify contour keypoints which produce a triangulated surface suitable for generating contours.
' ClsLst - ???????? ????? ?????, example "2,14"
' ToClass - ????? ?????????? (?.?. ? ????? ????? ??????????????????)
' Interval - contour interval (m)
' Init - initial sampling distance (m)
' Lim - limit for classification (1=accure/many points, 100=pretty/few points)
' Peaks - 0=no, 1=keep peaks and pits
' PeakArea - minimum area (m2) for peak to keep
' PitArea - minimum area (m2) for pit to keep
' Fence, ???? 0 - ?? ??? ?????, ???? 1, ?? ?????? ?????
' ?????????? ?????????? ?????????????????? ????? (0...n)
' ?????? -1 ???? ???? ?? ??????, ?? ??? ???? ???????? ?????? ?????? ?????
' ?????? -2 ???? ????????
' ?????? -3 ???? ????????? ????????
Function FnScanClassifyContourKey(ByVal ClsLst As String, ByVal ToClass As Long, ByVal Interval As Double, ByVal Init As Double, _
                                  ByVal Lim As Long, ByVal Peaks As Long, ByVal PeakArea As Double, ByVal Fence As Long) As Long
    FnScanClassifyContourKey = GetCExpressionValue("FnScanClassifyContourKey(" & StrPtr(StrConv(ClsLst & vbNullChar, vbFromUnicode)) & "," & ToClass & "," & Interval & "," & Init & "," & _
                                                                                 Lim & "," & Peaks & "," & PeakArea & "," & Fence & ")")
End Function

' ????????????? ????? ???????????? ??????????? Centerline.
' ClsLst - ???????? ????? ?????, example "2,14"
' ToClass - ????? ?????????? (?.?. ? ????? ????? ??????????????????)
' Cmp - compare with 0=any line, 1=closest line
' Side - -1=left, 0=either, 1=right side
' OffMin - minimum xy offset from element (m)
' OffMax - maximum xy offset from element (m)
' UseDz - if true, use dz from alignment
' DzMin - minimum dz value
' DzMax - maximum dz value
' UseDst - if true, use distance from closest vertex
' DstMin - minimum longitudinal distance to vertex
' DstMax - minimum longitudinal distance to vertex
' ?????????? ?????????? ?????????????????? ????? (0...n)
' ?????? -1 ???? ???? ?? ??????, ?? ??? ???? ???????? ?????? ?????? ?????
' ?????? -2 ???? ????????
' ?????? -3 ???? ????????? ????????
Function FnScanClassifyCtrline(ByVal ClsLst As String, ByVal ToClass As Long, ByVal Cmp As Long, _
                               ByVal Side As Long, ByVal OffMin As Double, ByVal OffMax As Double, _
                               ByVal UseDz As Long, ByVal DzMin As Double, ByVal DzMax As Double, _
                               ByVal UseDst As Long, ByVal DstMin As Double, ByVal DstMax As Double) As Long
    FnScanClassifyCtrline = GetCExpressionValue("FnScanClassifyCtrline(" & StrPtr(StrConv(ClsLst & vbNullChar, vbFromUnicode)) & "," & ToClass & "," & Cmp & "," & _
                                                                           Side & "," & OffMin & "," & OffMax & "," & _
                                                                           UseDz & "," & DzMin & "," & DzMax & "," & _
                                                                           UseDst & "," & DstMin & "," & DstMax & "," & ")")
End Function


' ????????????? ????? ?? ???????? Echo
' FromClass - ???????? ????? ????? (???????? 999 - ??? ??????)
' ToClass - ????? ?????????? (?.?. ? ????? ????? ??????????????????)
' Echo - ???????? Echo
' Fence, ???? 0 - ?? ??? ?????, ???? 1, ?? ?????? ?????
' Valid values for Echo parameter are:
' 0 only Echo
' 1 first of many
' 2 intermediate
' 3 last of many
' 11 any first (only echo or first of many)
' 13 any last (only echo or last of many)
' ?????????? ?????????? ?????????????????? ????? (0...n)
' ?????? -1 ???? ???? ?? ??????, ?? ??? ???? ???????? ?????? ?????? ?????
' ?????? -3 ???? ????????? ????????
Function FnScanClassifyEcho(ByVal FromClass As Long, ByVal ToClass As Long, ByVal Echo As Long, ByVal Fence As Long) As Long
    FnScanClassifyEcho = GetCExpressionValue("FnScanClassifyEcho(" & FromClass & "," & ToClass & "," & Echo & "," & Fence & ")")
End Function


' ????????????? ????? ?? ??????????? ???????????? ??? ????? edge
' FromClass - ???????? ????? ????? (???????? 999 - ??? ??????)
' ToClass - ????? ?????????? (?.?. ? ????? ????? ??????????????????)
' Direction - 0=negative direction, 1=positive direction, 2=edge
' Fence, ???? 0 - ?? ??? ?????, ???? 1, ?? ?????? ?????
' ?????????? ?????????? ?????????????????? ????? (0...n)
' ?????? -1 ???? ???? ?? ??????, ?? ??? ???? ???????? ?????? ?????? ?????
' ?????? -2 ???? ??? ??????????? ????????????
' ?????? -3 ???? ????????? ????????
Function FnScanClassifyDirection(ByVal FromClass As Long, ByVal ToClass As Long, ByVal Direction As Long, ByVal Fence As Long) As Long
    FnScanClassifyDirection = GetCExpressionValue("FnScanClassifyDirection(" & FromClass & "," & ToClass & "," & Direction & "," & Fence & ")")
End Function

' Classify points which are hits on building roofs.
' GrdClass - ????? ?????
' FromClass - ???????? ????? (high vegetation)
' ToClass - ????? ?????????? (?.?. ? ????? ????? ??????????????????)
' MinArea - ??????????? ??????? ?????? (m2)
' Tol -  plane tolerance (m)
' UseEcho - use echo information?
' Fence, ???? 0 - ?? ??? ?????, ???? 1, ?? ?????? ?????
' ?????????? ?????????? ?????????????????? ????? (0...n)
' ?????? -1 ???? ???? ?? ??????, ?? ??? ???? ???????? ?????? ?????? ?????
' ?????? -3 ???? ????????? ????????
Function FnScanClassifyBuilding(ByVal GrdClass As Long, ByVal FromClass As Long, ByVal ToClass As Long, ByVal MinArea As Double, ByVal Tol As Double, ByVal UseEcho As Long, ByVal Fence As Long) As Long
    FnScanClassifyBuilding = GetCExpressionValue("FnScanClassifyBuilding(" & GrdClass & "," & FromClass & "," & ToClass & "," & MinArea & "," & Tol & "," & UseEcho & "," & Fence & ")")
End Function

' ????????????? ????? ?????? ?????, ??????? ????????? ? ???????? ???? ???????? DGN ??? ?????????
' ClsLst - ???????? ????? ?????, example "2,14"
' ToClass - ????? ?????????? (?.?. ? ????? ????? ??????????????????)
' Lvl Level
' ByClr filter by color?
' Clr -Color
' ByWgt filter by weight?
' Wgt -Weight
' BySty filter by style?
' Sty -Style
' Dgn 0=active design and references, 1=active design file, 2=reference files
' ?????????? ?????????? ?????????????????? ????? (0...n)
' ?????? -2 ???? out of memory.
Function FnScanClassifyShapes(ByVal ClsLst As String, ByVal ToClass As Long, ByVal Lvl As Long, ByVal Clr As Long, _
                                ByVal ByWgt As Long, ByVal Wgt As Long, ByVal BySty As Long, ByVal Sty As Long, ByVal Expand As Double, ByVal Dgn As Long) As Long
    FnScanClassifyShapes = GetCExpressionValue("FnScanClassifyShapes(" & StrPtr(StrConv(ClsLst & vbNullChar, vbFromUnicode)) & "," & FromClass & "," & Lvl & "," & Clr & "," & _
                                                                         ByWgt & "," & Wgt & "," & BySty & "," & Sty & "," & Expand & "," & Dgn & ")")
End Function

' ????????????? ?????, ? ??????? Mark = 1
' Return number of classified points.
Function FnScanClassifyMarked(ByVal FromClass As Long, ByVal ToClass As Long) As Long
    FnScanClassifyMarked = GetCExpressionValue("FnScanClassifyMarked(" & FromClass & "," & ToClass & ")")
End Function

' ???????? ????? ?? ??????
' Class source class to delete
' Fence 0=all points, -1=outside fence, 1=inside fence
' Return number of points deleted (0...n).
' Return -1 if no fence defined (and Fence was nonzero).
Function FnScanDeleteClass(ByVal Class As Long, ByVal Fence As Long) As Long
    FnScanDeleteClass = GetCExpressionValue("FnScanDeleteClass(" & Class & "," & Fence & ")")
End Function

' ???????? ????? ?? ?????????
' Line flightline or measurement to delete
' Fence 0=all points, -1=outside fence, 1=inside fence
' Return number of points deleted (0...n).
' Return -1 if no fence defined (and Fence was nonzero).
Function FnScanDeleteLine(ByVal line As Long, ByVal Fence As Long) As Long
    FnScanDeleteLine = GetCExpressionValue("FnScanDeleteLine(" & line & "," & Fence & ")")
End Function

' ????????????? ?????
' FromClass - ???????? ????? ????? (???????? 999 - ??? ??????)
' Name - ???????? ????????????? ? ?????????? TerraScan
' Fence 0=all points, 1=inside fence
' Return number of points deleted (0...n).
' Return -1 if no fence defined (and Fence was nonzero).
' Return -2 if was aborted.
' Return -3 if invalid parameters.
' Return -4 if transformation was not found.
Function FnScanTransform(ByVal Class As Long, ByVal Name As String, ByVal Fence As Long) As Long
    FnScanTransform = GetCExpressionValue("FnScanTransform(" & line & "," & StrPtr(StrConv(Name & vbNullChar, vbFromUnicode)) & "," & Fence & ")")
End Function

' ??????????? ???? ????, ?? ??????? ????? ???? ?????????? ?????
' ?????? ?????????? 1
Function FnScanUpdateViews() As Long
    FnScanUpdateViews = GetCExpressionValue("FnScanUpdateViews()")
End Function

' ?????????? ??????????? ?????
' 0 increasing easting
' 1 decreasing northing
' 2 increasing easting
' 3 decreasing northing
' 4 increasing time stamp
' 19 MDL Public Functions
' Return 1 if points were sorted.
' Return 0 if nothing was done.
Function FnScanSort(ByVal By As Long) As Long
    FnScanSort = GetCExpressionValue("FnScanSort(" & By & ")")
End Function

' Output points to a file.
' File - Output file name. If it contains string "######", that string will be replaced by active block number.
'        Active project directory will be used if File does not include a directory specification.
'        If File contains string "#name", that string will replaced by active file name.
'        In that case, File should always include directory and extension such as "c:\output\#name.grd".
' ClsLst - list of classes to output, example "1,7-9"
' Fmt - Format of output file.
' Delim - Delimiter (0=space, 1=tabulator, 2=comma).
' Trans - Name of transformation in TerraScan settings.
' Pass - zero or "" for none.
' Append - If true, add to end of a possibly existing file.
' Fence - 0=all points, 1=inside fence
' Format can be:
' 1 X Y Z
' 2 Class X Y Z
' 3 X Y Z Intensity
' 5 Class X Y Z Intensity
' 7 TerraScan binary 8 bit line numbers
' 8 TerraScan binary 16 bit line numbers
' 13 EarthData binary
' 23 Grass Sites format
' 200+ User defined file format
' Return number of points written.
' Return -1 if no fence defined (and Fence was nonzero).
' Return -2 if failed to write to file.
' Return -3 if invalid parameters.
' Return -4 if transformation was not found.
Function FnScanOutput(ByVal File As String, ByVal ClsLst As String, ByVal Fmt As Long, ByVal Delim As Long, ByVal nDelim As Long, ByVal Trans As String, ByVal Append As Long, ByVal Fence As Long, ByVal Block As Long, ByVal Val As Long) As Long
    FnScanOutput = GetCExpressionValue("FnScanOutput(" & StrPtr(StrConv(File & vbNullChar, vbFromUnicode)) & "," & _
                                                         StrPtr(StrConv(ClsLst & vbNullChar, vbFromUnicode)) & "," & _
                                                         Fmt & "," & _
                                                         Delim & "," & _
                                                         nDelim & "," & _
                                                         StrPtr(StrConv(Trans & vbNullChar, vbFromUnicode)) & "," & _
                                                         Append & "," & _
                                                         Fence & "," & _
                                                         Block & "," & Val & ")")
End Function

' Output points to a file based on flightline number. This will generate multiple output files if Line == -1 in which case one output file will be generated for every flightline.
' File - Output file name. If File contains string "#line", that string will be replaced by flight line number.
'        Active project directory will be used if File does not include a directory specification.
'        Line Line to output. Pass -1 for all lines and use "#line" as part of file name.
' Class - Class of points to output. Pass 999 for all points.
' Fmt - Format of output file, see FnScanOutput().
' Delim - Delimiter (0=space, 1=tabulator, 2=comma).
' Trans - Name of transformation in TerraScan settings. Pass zero or "" for none.
' Append - If true, add to end of a possibly existing file.
' Return number of points written.
' Return -3 if invalid parameters.
' Return -4 if transformation was not found.
Function FnScanOutputLine(ByVal File As String, ByVal line As Long, ByVal Class As Long, ByVal Fmt As Long, ByVal Delim As Long, _
                          ByVal Trans As String, ByVal Append As Long) As Long
    FnScanOutputLine = GetCExpressionValue("FnScanOutputLine(" & StrPtr(StrConv(File & vbNullChar, vbFromUnicode)) & "," & line & "," & Class & "," & _
                                                                 Fmt & "," & Delim & "," & StrPtr(StrConv(Trans & vbNullChar, vbFromUnicode)) & "," & Append & ")")
End Function

' Return information about the active project. Set:
' Type - project type: 0=airborne, 1=ground based
' Fmt - storage format: 0=TerraScan binary, 1=EarthData
' ???????? FMT ? ???????????? ??????????. ?? ???? ?????? ???:
' 0 - Bin 8 bit
' 1 - Bin 16 bit
' 2 - EarthData EEBN ? EBN
' 3 - LAS 1.0
' 4 - LAS 1.1
' 5 - LAS 2.0
' 6 - FastBin
' Dir - data file directory
' Return number of blocks (0 - n).
' Return -1 if no active project.
' ????????? ???????? ??? ByRef, ?.?. ??????? ?? ??????!
' ????????? ?????? ??????? ? ???, ??? ?????? ????????? ???????????? ?????? ???????? Dir (char *Dir)
' ? VBA ?? ????? ????????? ?? ?????, ?.?. ?? ?? ????? ????? ????? ? ????? ?? ???????? ??????, ?.?. ?? ??????? ?? ????? ??????? ??? ???? ???? ??????? ?? ?????????
' ??? ????? ???????? ???????? ?????? Dir ????????????? (???????? 10 000 ????????), ????????????? ? ???????? ????? ? ????? ??????? ?????
Function FnScanProjectInfo(ByRef Typep As Long, ByRef Fmt As Long, ByRef Dir As String) As Long
    Dim i As Long
    Dim bytArr() As Byte
    bytArr = StrConv(Dir & vbNullChar, vbFromUnicode)
    
    FnScanProjectInfo = GetCExpressionValue("FnScanProjectInfo(" & VarPtr(Typep) & "," & VarPtr(Fmt) & "," & VarPtr(bytArr(0)) & ")")
    
    Dir = ""
    For i = LBound(bytArr) To UBound(bytArr)
        Dir = Dir + Chr(bytArr(i))
    Next i
End Function

' Return information about project block index Ind. Set:
' Vrt[] boundary vertices (up to 41)
' File binary file name including full path
' Return number of boundary vertices (0 - 41).
' Return -1 if invalid index or no active project.
' ?????????? ?????? ? 0
' Vrt() - ?????? ?? ????????????, ? ??????????? ?? 5000 ?????????. ????? ?????????? ??????? ?? ?????????? ????????? ???????, ??????? ?????? ??????? ? ???? ??????
' File - ?????????? DIR ?????????? ??????? FnScanProjectInfo
Function FnScanProjectBlock(ByRef Vrt() As Point3d, ByRef File As String, ByVal Ind As Long) As Long
    Dim i As Long
    Dim bytArr() As Byte
    bytArr = StrConv(File & vbNullChar, vbFromUnicode)
    
    FnScanProjectBlock = GetCExpressionValue("FnScanProjectBlock(" & VarPtr(Vrt(0)) & "," & VarPtr(bytArr(0)) & "," & Ind & ")")
    
    File = ""
    For i = LBound(bytArr) To UBound(bytArr)
        File = File + Chr(bytArr(i))
    Next i
End Function

' Create lattice model from laser points in class Class and write that to file File.
' File - Output file name. Active project directory will be used if File does not include a directory specification.
'        If it contains string "######" or "#block", that string will be replaced by active block number.
'        If File contains string "#name", that string will be replaced by active file name.
'Class - Class of points to output. Pass 999 for all points.
'Elev - 0=lowest, 1=average, 2=highest hit, 3=triangle model
'Step - Grid step size (m).
'Len - Number of gap pixels to fill if Elev != 3. Maximum triangle length if Elev == 3.
'Fmt - Format of output file.
'UnitZ - Unit of Z values: 0=uor, 1=mm, 2=cm, 3=dm, 4=m. Used only with Intergraph and Raw binary formats.
'CrdBlk - 0=no coordinate block, nonzero=output. Used only with Intergraph format.
'Out - Value to output in undefined area. Pass NULL to skip. Used only with ArcInfo and Xyz text formats.
' Format can be:
' 0 Intergraph Grd
' 5 Raw binary 16 bit
' 6 Raw binary 32 bit
' 7 Raw binary 64 bit double
' 8 ArcInfo GRIDASCII
' 9 Xyz Text
' Return 1 on success.
' Return 0 if no source points.
' Return -2 if failed to write to file.
Function FnScanExportLattice(ByVal File As String, ByVal Class As Long, ByVal Elev As Long, ByVal Step As Double, ByVal lenn As Double, ByVal Fmt As Long, _
                             ByVal UnitZ As Long, ByVal CrdBlk As Long, ByVal Out As String) As Long
    FnScanExportLattice = GetCExpressionValue("FnScanExportLattice(" & StrPtr(StrConv(File & vbNullChar, vbFromUnicode)) & "," & Class & "," & Elev & "," & _
                                                                       Step & "," & lenn & "," & Fmt & "," & UnitZ & "," & CrdBlk & "," & _
                                                                       StrPtr(StrConv(Out & vbNullChar, vbFromUnicode)) & ")")
End Function

' Read points from file File into RAM.
' File Full path of input file(s). Multiple file names should be separated by '\n'
' First - Class for non-last echos (if not in input)
' Last - Class for last echos (if not in input)
' Line - Flightline number (if not in input)
' Inc - When flightline number is incremented. 0=never, 2=new file, 3=new file name, 4=new dir
' Trans - Name of transformation in TerraScan settings. Pass zero or "" for none
' Fence - 0=all points, 1=inside fence
' Every - 0=every, 1=every, n=every n:th
' Return number of points found.
' Return -2 if failed to open or recognize format of first file.
' Return -3 if invalid parameters.
' Return -4 if transformation was not found.
' Return -5 if out of memory.
Function FnScanRead(ByVal File As String, ByVal First As Long, ByVal Last As Long, ByVal line As Long, ByVal Inc As Long, ByVal Trans As String, ByVal Fence As Long, ByVal Every As Long) As Long
    FnScanRead = GetCExpressionValue("FnScanRead(" & StrPtr(StrConv(File & vbNullChar, vbFromUnicode)) & "," & First & "," & Last & "," & _
                                                     line & "," & Inc & "," & StrPtr(StrConv(Trans & vbNullChar, vbFromUnicode)) & "," & Fence & "," & Every & ")")
End Function

' Smoothen surface by adjusting point elevations. moving points points by adjusting elevations by a maximum of
' ModLst - classes to smoothen, example "1,7-9"
' UpCm - maximum movement up (cm)
' DnCm - maximum movement down (cm)
' FixLst - immovable classes to include in surface, "5-6"
' Fence - 0=all points, -1=outside fence, 1=inside fence
' Return 1 if points were adjusted.
' Return 0 if nothing was done.
' Return -2 if out of memory.
Function FnScanSmoothen(ByVal ModLst As String, ByVal UpCm As Long, ByVal DnCm As Long, ByVal FixLst As String, ByVal Fence As Long) As Long
    FnScanSmoothen = GetCExpressionValue("FnScanSmoothen(" & StrPtr(StrConv(ModLst & vbNullChar, vbFromUnicode)) & "," & UpCm & "," & DnCm & "," & _
                                                             StrPtr(StrConv(FixLst & vbNullChar, vbFromUnicode)) & "," & Fence & ")")
End Function

' Thin data set by removing points close to another point. Point can be removed if it is within Dxy horizontal distance and Dz elevation difference from another point.
' Class - source class to thin (999 for any)
' Keep point to keep in a group: 0=highest,1=lowest,2=central,3=create average
' Dxy - xy distance limit
' Dz - dz limit
' Fence - 0=all points, -1=outside fence, 1=inside fence
' Return number of points removed (0...n).
' Return -1 if no fence defined (and Fence was nonzero).
' Return -3 if invalid parameters.
Function FnScanThinPoints(ByVal Class As Long, ByVal Keep As Long, ByVal Dxy As Double, ByVal dz As Double, ByVal Fence As Long) As Long
    FnScanThinPoints = GetCExpressionValue("FnScanThinPoints(" & Class & "," & Keep & "," & Dxy & "," & dz & "," & Fence & ")")
End Function

' Cut points from overlapping flightlines by either flightline quality or by offset from trajectory.
' ClsLst - List of coverage classes, example "0-255"
' Action - Action: 0=add constant, 1=classify, 2=delete
' Val - If Action == 0, value to add to class
'       If Action == 1, class to classify to
'       If Action == 2, ignored
' Quality - 0=no, 1=cut by trajectory quality
' Gap - radius of empty area to consider a gap
' Offset 0=no, 1=cut by offset
' Keep - minimum corridor to keep (degrees)
' Return number of points affected (0...n).
' Return -3 if invalid parameters.
' Return -4 if no trajectories.
Function FnScanCutOverlap(ByVal ClsLst As String, ByVal Action As Long, ByVal Val As Long, ByVal Quality As Long, ByVal Gap As Double, ByVal Offset As Long, ByVal Keep As Long) As Long
    FnScanCutOverlap = GetCExpressionValue("FnScanCutOverlap(" & StrPtr(StrConv(ClsLst & vbNullChar, vbFromUnicode)) & "," & Action & "," & Val & "," & Quality & "," & Gap & "," & Offset & "," & Keep & ")")
End Function

' Adjust laser points using an angular change to the vector from scanner position to the point.
' Line Line to adjust. Pass -1 for all lines.
' Fix Coordinate axis to fix: 1=z, 2=xy, 3=xyz
' Input Angle unit used: 0=degrees, 1=radians, 2=ratio
' Head Heading correction angle
' Roll Roll correction angle
' Pitch Pitch correction angle
' Div Angle divider corresponding to full circle.
' Used if Input == 2.
' Return number of points adjusted.
' Return -1 if no trajectories loaded.
Function FnScanAdjustAngles(ByVal line As Long, ByVal Fixx As Long, ByVal Inputt As Long, ByVal Head As Double, ByVal Roll As Double, ByVal Pitch As Double, ByVal Div As Double) As Long
    FnScanAdjustAngles = GetCExpressionValue("FnScanAdjustAngles(" & line & "," & Fixx & "," & Inputt & "," & Head & "," & Roll & "," & Pitch & "," & Div & ")")
End Function

' ??????? FnScanMarkAll ???????? ??? ??????????? ????? ??????? ????????? Mark
Function FnScanMarkAll(ByVal MarkVal As Long) As Long
    FnScanMarkAll = GetCExpressionValue("FnScanMarkAll(" & MarkVal & ")")
End Function

' ??????? FnScanMarkFence ???????? ????? ?????? ????? ????????? 1, ??? ????? ????????? 0
' Fst ? Lst ???????? ??????????? ?? ?????? ? ????????? ????? ?????? ?????
' ?????????? 1 ???? ??????????, 0 ???? ??????
Function FnScanMarkFence(ByRef Fst As Long, ByRef Lst As Long) As Long
    FnScanMarkFence = GetCExpressionValue("FnScanMarkFence(" & VarPtr(Fst) & "," & VarPtr(Lst) & ")")
End Function

' Fill option button with class names.
' Return 0 always.
' ????????: ??????? ?? ????????! ???? ????????????? ????????? rawitemhdr, ??????? ??????? c:\Program Files (x86)\Bentley\MicroStation\mdl\include\dlogitem.h
Function FnScanClassOption(ByRef Raw As Long) As Long
    FnScanClassOption = GetCExpressionValue("FnScanClassOption(" & VarPtr(Sel) & ")")
End Function

'Fill string list with:
'- class numbers and names if Nbr is true
'- class names only if Nbr is zero
'Return number of classes.
' ????????: ??????? ?? ????????! Lst ????? ??? StringList, ?????? ???????? ???? ????? ? VBA
Function FnScanClassList(ByRef Lst() As String, ByVal Nbr As Long) As Long
    FnScanClassList = GetCExpressionValue("FnScanClassList(" & VarPtr(Lst(0)) & "," & Nbr & ")")
End Function

' ??????? FnScanSelectClasses ??????? ?????????? ????? ?? ??????? ????????? ???????
' ? ???????? Sel ?????????? 0-?? ??????? ???????? ???????????? ??????? ?? 256 ????????? (Dim Sel(255) As Byte)
' ?????????? ?????????? ?????????? ??????? ? ??????????? ?????? (0 - ?? ???????, 1 - ???????)
' ???? ?????? ?????? Cancel, ?? ?????? -1
Function FnScanSelectClasses(ByRef Sel As Byte) As Long
    FnScanSelectClasses = GetCExpressionValue("FnScanSelectClasses(" & VarPtr(Sel) & ")")
End Function

' ??????? FnScanSave ????????? ??????????? ????? ?? ????????? ???? ? ???????? ???????
' ?????????? 1 ???? ?????? ???????, 0 - ???? ????????? ??????
' ????????: StrPtr ??? ???? ????? ??????????. ?? ??? ??? ???? ??????? ??????? ?? ????? char *Path (?????? ????????), ?? ???? ????? ??????? ??????????????
' ? ???????? ??????, ?????? ?????? LPSTR (ANSI  ? ???????? Char(0) ? ?????)
' ?????? ??????? ??????? ???: http://www.sql.ru/forum/505264-2/peredacha-char-cherez-vba-v-dll
Function FnScanSave(ByVal Path As String) As Long
    FnScanSave = GetCExpressionValue("FnScanSave(" & StrPtr(StrConv(Path & vbNullChar, vbFromUnicode)) & ")")
End Function

' ??????? ????????????? ????? ?? ?????????? ?????
' ?????????? 1 ???? ???????, 0 ???? ?????? ?????? ?????,
' -1 - ???? ? ??? ? ?????? ??? ???? ?????, -2 - ???? ?????? Out of memory (?????? ?? ??????? ?????? ??? ????????)
' ??? ????? ??????????: ? ??? ?????? TerraScan, ????? ???. ????????? ????? ???? ???????? - ? ?????? ??? ????, ?? ??? ?? ???????????? (???????? ????????? ???
' ??? ????? ?????????. Fit View ???????? ?????????? ?????, ?? ??? ?? ????????)
Function FnScanReload(ByVal Path As String) As Long
    FnScanReload = GetCExpressionValue("FnScanReload(" & StrPtr(StrConv(Path & vbNullChar, vbFromUnicode)) & ")")
End Function

' ??????? FnScanPreFree ?????????? ????????? ????? FnScanFreeTable
' ??????????? ???????????? ? ??????? ????????? ???????????????? ?????? ????? ?????????
' ?????????? 1 ???? ???? ????????? (?????? ?????? Yes)
' ?????????? 0 ???? ????? ??? ??? ??? ?? ???? ???????????????
Function FnScanPreFree() As Long
    FnScanPreFree = GetCExpressionValue("FnScanPreFree()")
End Function

' ??????? FnScanFreeTable ??????????? ?????????????? ??? ????? ??????
' ??????? ???????? ???????????? ?? ??????!!!
' ?????????? ???, ?????? ?????????? 1
Function FnScanFreeTable() As Long
    FnScanFreeTable = GetCExpressionValue("FnScanFreeTable()")
End Function

' Find laser point closest to point Cp which is within distance R of point Cp when drawn in view Vw.
' Fp Point where the coordinates will be stored.
' Class Class of points to output. Pass 999 for all points.
' Cp Point at which to search.
' R Search radius (m).
' Vw View index for rotation of search (pass -1 for top view search logic).
' Return index of point if found (0,1,2,...).
' Return -1 if no point found.
Function FnScanFindClosest(ByRef Fp As Point3d, ByVal Class As Long, ByRef CP As Point3d, ByVal r As Double, ByVal Vw As Long) As Long
    FnScanFindClosest = GetCExpressionValue("FnScanFindClosest(" & VarPtr(Fp) & "," & Class & "," & VarPtr(CP) & "," & r & "," & Vw & ")")
End Function

Attribute VB_Name = "LCE_AxisToCentrline"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private FirstLine As LineElement

Private Sub ILocateCommandEvents_Accept(ByVal Element As Element, point As Point3d, ByVal View As View)
    Dim myEnum As ElementEnumerator
    Dim myFilter As New ElementScanCriteria
    Dim mLine() As Element
    Dim tempLine As LineElement
    Dim mCentrline() As Point3d
    Dim cLine As LineElement

        
    myFilter.ExcludeAllTypes
    myFilter.ExcludeAllLevels
    myFilter.ExcludeAllColors
    
    myFilter.IncludeType msdElementTypeLine
    myFilter.IncludeLevel FirstLine.Level
    myFilter.IncludeColor FirstLine.Color
        
    Set myEnum = ActiveModelReference.Scan(myFilter)
    mLine = myEnum.BuildArrayFromContents
    DelInitialElement mLine, FirstLine
    
    Dim i As Long
    RedimPreserve mCentrline
    mCentrline(UBound(mCentrline)) = SelectToBottomOfLine(FirstLine)
    For i = 0 To UBound(mLine)
        RedimPreserve mCentrline
        Set tempLine = FindMinDistanceElement(mLine, FirstLine)
        mCentrline(UBound(mCentrline)) = SelectToBottomOfLine(tempLine)
        Set FirstLine = tempLine
    Next i
    
    Set cLine = CreateLineElement1(Nothing, mCentrline)
    cLine.Level = CheckLevel(UserForm1.TextBox_LevelForCentreline.Text)
    
    ActiveModelReference.AddElement cLine
    cLine.Redraw
    

End Sub
Private Sub DelInitialElement(ByRef mArr() As Element, mLine As LineElement)
    Dim i As Long
    
    For i = 0 To UBound(mArr)
        If mLine.FilePosition = mArr(i).FilePosition Then
            DeleteElementOfArray mArr, i
            Exit For
        End If
    Next i
End Sub
Private Sub RedimPreserve(ByRef mB() As Point3d)
    Dim i As Long
    On Error Resume Next
    i = UBound(mB) + 1
    If Err.Number = 9 Then
        ReDim mB(0)
    Else: ReDim Preserve mB(i)
    End If
    Err.Clear
End Sub
Private Function SelectToBottomOfLine(mLine As LineElement) As Point3d
    Dim topPoint As Point3d
    Dim bottomPoint As Point3d
    
    If mLine.startPoint.Z > mLine.EndPoint.Z Then
        topPoint = mLine.startPoint
        bottomPoint = mLine.EndPoint
    Else
        topPoint = mLine.EndPoint
        bottomPoint = mLine.startPoint
    End If
    
    If UserForm1.OptionButton_TopOfAxis.Value Then
        SelectToBottomOfLine = topPoint
    ElseIf UserForm1.OptionButton_BottomOfAxis.Value Then
        SelectToBottomOfLine = bottomPoint
    End If
End Function


Private Function FindMinDistanceElement(ByRef mAxis() As Element, ByVal mLine As LineElement) As LineElement
    Dim minDist As Double, dist As Double
    Dim m As Long
    Dim line As LineElement
    Dim iniLineP As Point3d
    Dim serchLinePoint As Point3d
    
    iniLineP = SelectToBottomOfLine(mLine)
    
    
    Set line = mAxis(0).AsLineElement
    minDist = Point3dDistance(iniLineP, SelectToBottomOfLine(line))
    m = 0
    For i = 0 To UBound(mAxis)
        Set line = mAxis(i).AsLineElement
        dist = Point3dDistance(iniLineP, SelectToBottomOfLine(line))
        If minDist > dist Then
            minDist = dist
            m = i
        End If
    Next i
    Set FindMinDistanceElement = mAxis(m).AsLineElement
    If UBound(mAxis) > 0 Then DeleteElementOfArray mAxis, m
End Function
Function CheckLevel(LevelName As String) As Level
    Dim MyLevel As Level
    On Error Resume Next
    
    Set CheckLevel = ActiveDesignFile.Levels(LevelName)
    If Err.Number <> 0 And LevelName <> "" Then
         Set MyLevel = ActiveDesignFile.AddNewLevel(LevelName)
         ActiveDesignFile.Levels.Rewrite
         MsgBox "Создан слой: " & LevelName
         Set CheckLevel = MyLevel
    End If
    Err.Clear
End Function
Private Sub DeleteElementOfArray(ByRef mArr() As Element, i As Long)
    Dim k As Long
    
    For k = i To UBound(mArr) - 1
        Set mArr(k) = mArr(k + 1)
    Next k
    ReDim Preserve mArr(UBound(mArr) - 1)
End Sub
Private Sub ILocateCommandEvents_Cleanup()

End Sub

Private Sub ILocateCommandEvents_Dynamics(point As Point3d, ByVal View As View, ByVal DrawMode As MsdDrawingMode)

End Sub

Private Sub ILocateCommandEvents_LocateFailed()
'    If UserForm_Cell_to_Point.ComboBox_cell.Text = "" Then
'        MsgBox "Выберите Cell"
'    End If
End Sub

Private Sub ILocateCommandEvents_LocateFilter(ByVal Element As Element, point As Point3d, Accepted As Boolean)
Accepted = False
If Element.IsLineElement Then 'And Element.AsCellElement.Name = UserForm_Cell_to_Point.ComboBox_cell.Text
    Accepted = True
    Set FirstLine = Element.AsLineElement
    'CellName = Element.AsCellElement.Name
   ' UserForm_Cell_to_Point.Label6.Caption = Element.AsCellElement.Name
End If
ShowCommand "Axis To Centreline"
ShowPrompt "Подтвердите выделение ЛКМ"
End Sub

Private Sub ILocateCommandEvents_LocateReset()

End Sub

Private Sub ILocateCommandEvents_Start()
    'CommandState.EnableAccuSnap
    ShowCommand "Axis To Centreline"
    ShowPrompt "Укажите начальный Axis"
End Sub

Attribute VB_Name = "Module1"
Sub Main()
    UserForm1.Show vbmodells
    
End Sub

Attribute VB_Name = "PCE_PlaceCellRotate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private bPoint          As Point3d ' Точка вставки Cell
Private sPoint          As Point3d ' Вторая точка
Private fdPoint         As Point3d '
Private FirstPoint      As Boolean ' Проверка на первую точку
Private Second          As Boolean
Private moveCell        As Boolean
Private CellName        As String
Private MyCell          As CellElement
Private prPointOnPlan   As Point3d
Private rotation        As Matrix3d
Private dRotation       As Matrix3d

Dim VerticalLine As LineElement ' Вертикальная линия
Implements IPrimitiveCommandEvents
Private Sub IPrimitiveCommandEvents_Cleanup()
End Sub

Private Sub IPrimitiveCommandEvents_DataPoint(point As Point3d, ByVal View As View)
Dim tmpCell         As CellElement
Dim rotation        As Matrix3d
Dim RotationMatrix  As Matrix3d
Dim OriginAccu      As Point3d
Dim oClone          As Element

Dim origin          As LineElement

Dim tmpVertLine As LineElement
    
    If FirstPoint = False And Second = False Then ' ***** -1-
        bPoint = point
        FirstPoint = True
        If UserForm1.CheckBox_cross_view.Value = True Then
            CrossSection CInt(UserForm1.ComboBox_inView.Text), CInt(UserForm1.ComboBox_CrossView.Text)
        End If
        If UserForm1.CheckBox_AdjustZ.Value Then AdjustZOn
'        If UserForm1.CheckBox_AdjustZ.Value Then AdjustZOff
    ElseIf FirstPoint = True Then ' ***** -2-
        If (Not UserForm1.CheckBoxLockHeight.Value) And UserForm1.CheckBox_AdjustZ.Value Then
            sPoint = ActiveDepthDraw(View, bPoint, point)
            Set VerticalLine = CreateLineElement2(Nothing, bPoint, sPoint)
        End If
            
        ActiveModelReference.AddElement VerticalLine
        VerticalLine.Redraw
        Second = True
        moveCell = True
        FirstPoint = False
        fdPoint = point
        If UserForm1.CheckBox_AdjustZ.Value Then AdjustZOff
    ElseIf moveCell = True Then
        VerticalLine.Redraw msdDrawingModeTemporaryErase
        VerticalLine.Move Point3dSubtract(ActiveDepthDraw(View, bPoint, point), bPoint)
        VerticalLine.Redraw msdDrawingModeNormal
        VerticalLine.Rewrite
       '' If UserForm1.CheckBoxLockHeight.Value Then
            fdPoint = Point3dAddPoint3dVector3d(fdPoint, Vector3dSubtractPoint3dPoint3d(ActiveDepthDraw(View, bPoint, point), bPoint))
       ' Else
           ' fdPoint.Z = fdPoint.Z - Point3dDistance(fdPoint, ActiveDepthDraw(View, bPoint, Point))
       ' End If
        bPoint = ActiveDepthDraw(View, bPoint, point)
        moveCell = False
    ElseIf Second = True Then
        Set tmpVertLine = ActiveModelReference.GraphicalElementCache.GetLastValidElement.AsLineElement
        ActiveModelReference.RemoveElement tmpVertLine
        tmpVertLine.Redraw
        ActiveModelReference.AddElement VerticalLine
        VerticalLine.Redraw
    End If

End Sub

Private Sub IPrimitiveCommandEvents_Dynamics(point As Point3d, ByVal View As View, ByVal DrawMode As MsdDrawingMode)
    Dim transform As Transform3d
    Dim RotationMatrix As Matrix3d
    Dim oClone          As Element
    
        If FirstPoint = False And Second = False Then
            sPoint = point
            sPoint.Z = point.Z - CDbl(UserForm1.TextBox_TowerHeight.Text)
            Set VerticalLine = CreateLineElement2(Nothing, point, sPoint)
            VerticalLine.Redraw DrawMode
        ElseIf moveCell = True Then
            Set oClone = VerticalLine.Clone
            oClone.Redraw msdDrawingModeTemporaryErase
            oClone.Move Point3dSubtract(ActiveDepthDraw(View, bPoint, point), bPoint)
            oClone.Redraw DrawMode
        ElseIf FirstPoint = True Then
            rotation = Matrix3dInverse(View.rotation)
            If UserForm1.CheckBoxLockHeight.Value Then
                sPoint.Z = bPoint.Z - CDbl(UserForm1.TextBox_TowerHeight.Text)
            Else
                sPoint = ActiveDepthDraw(View, bPoint, point)
            End If
            Set VerticalLine = CreateLineElement2(Nothing, bPoint, sPoint)
            If UserForm1.CheckBoxLockHeight.Value Then VerticalLine.transform SecondRotate(View, point)
            VerticalLine.Redraw DrawMode
        ElseIf FirstPoint = False And Second = True Then '  Крайний поворот
            sPoint = bPoint
            If UserForm1.CheckBoxLockHeight.Value Then
                sPoint.Z = bPoint.Z - CDbl(UserForm1.TextBox_TowerHeight.Text)
            Else
                sPoint.Z = bPoint.Z - VerticalLine.Length
            End If
            Set VerticalLine = CreateLineElement2(Nothing, bPoint, sPoint)
            VerticalLine.transform SecondRotate(View, ActiveDepthDraw(View, bPoint, point))
            VerticalLine.Redraw DrawMode
        End If
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
    CommandState.StartDynamics
    FirstPoint = False
        If UserForm1.CheckBox_cross_view.Value = True Then
            CrossSection CInt(UserForm1.ComboBox_inView.Text), CInt(UserForm1.ComboBox_CrossView.Text)
        End If
'        If UserForm1.CheckBox_AdjustZ.Value Then AdjustZOn
End Sub
Function Point3dToString(pnt As Point3d, myLable As Label) As String
    With pnt
        myLable.Caption = "X= " & Round(.x, 2) & vbCrLf & "Y= " & Round(.y, 2) & vbCrLf & "Z= " & Round(.Z, 2)
    End With
End Function

Function SecondRotate(dView As View, rotPoint As Point3d) As Transform3d
    Dim plan        As Plane3d
    Dim myRot       As Matrix3d
    Dim pntTemp     As Point3d
    Dim PerpVector  As Vector3d
    Dim tmpVector   As Vector3d
    Dim prBpoint    As Point3d
    
    If FirstPoint = True And Second = False Then
        With fdPoint
            .x = bPoint.x
            .y = bPoint.y
            .Z = 0
        End With
    End If
    
    prBpoint = bPoint
    prBpoint.Z = 0
    
    plan.origin = fdPoint
    plan.Normal = dView.rotation.RowZ
    
    If fdPoint.x <> bPoint.x And fdPoint.y <> bPoint.y Then
        plan.Normal = Point3dFromVector3d(Vector3dCrossProduct(Vector3dUnitPerpendicularXY(Vector3dFromPoint3d(Point3dSubtract(fdPoint, bPoint))), Vector3dSubtractPoint3dPoint3d(fdPoint, bPoint)))
    End If
    prPointOnPlan = Point3dProjectToPlane3d(rotPoint, plan)
    myRot = Matrix3dFromRotationBetweenVectors(Point3dSubtract(prBpoint, bPoint), Point3dSubtract(prPointOnPlan, bPoint))
    SecondRotate = Transform3dFromMatrix3dAndFixedPoint3d(myRot, bPoint)
    
End Function

Function ActiveDepthDraw(mView As View, aPoint As Point3d, tPoint As Point3d) As Point3d
    Dim mPlan         As Plane3d
    
    With mPlan
        .origin = aPoint
        .Normal = mView.rotation.RowZ
    End With
        ActiveDepthDraw = Point3dProjectToPlane3d(tPoint, mPlan)
End Function

Private Sub CrossSection(inV As Integer, crossV As Integer)
    Dim inView      As View
    Dim crossView   As View
    
    Dim origin      As LineElement
    Dim pP          As Point3d
    Dim pCenter     As Point3d
    
    Set inView = ActiveDesignFile.Views(inV)
    Set crossView = ActiveDesignFile.Views(crossV)
    
    crossView.SetArea Point3dAddPoint3dVector3d(inView.Center, Vector3dRotateXY(Vector3dSubtractPoint3dPoint3d(inView.origin, inView.Center), -Pi / 2)), inView.Extents, Matrix3dFromMatrix3dTimesMatrix3d(inView.rotation, Matrix3dFromAxisAndRotationAngle(2, Pi / 2)), inView.ActiveDepth
    crossView.Center = inView.Center
    crossView.Redraw
End Sub

Sub AdjustZOn()
    Dim startPoint As Point3d
    Dim point As Point3d, point2 As Point3d
    Dim lngTemp As Long

'   Start a command
    CadInputQueue.SendCommand "Mouse Point Adjustment"

'   Set a variable associated with a dialog box
    SetCExpressionValue "MpaAdjElev", -1, "TSCAN"

    SetCExpressionValue "MpaCalc", 4, "TSCAN"

    SetCExpressionValue "MpaClass", 2, "TSCAN"

    SetCExpressionValue "MpaWithin", 2, "TSCAN"
    'CommandState.StartDefaultCommand
End Sub

Sub AdjustZOff()
    Dim startPoint As Point3d
    Dim point As Point3d, point2 As Point3d
    Dim lngTemp As Long

'   Set a variable associated with a dialog box
    SetCExpressionValue "MpaAdjElev", 0, "TSCAN"

   ' CommandState.StartDefaultCommand
End Sub

Attribute VB_Name = "UserForm1"
Attribute VB_Base = "0{E14AF623-6E98-48C4-9C4A-8C3063C42253}{03BAA440-BFC7-495C-9F10-7E2C658DAF02}"
Attribute VB_GlobalNameSpace = False
Attribute VB_Creatable = False
Attribute VB_PredeclaredId = True
Attribute VB_Exposed = False
Attribute VB_TemplateDerived = False
Attribute VB_Customizable = False
Private Sub CommandButton_CreateCentreline_Click()
    CommandState.StartLocate New LCE_AxisToCentrline
End Sub

Private Sub CommandButton_DrawVertLine_Click()
    CommandState.StartPrimitive New PCE_PlaceCellRotate, True
End Sub



Private Sub UserForm_Initialize()
    MultiPage1.Value = 0
    IniNumView ComboBox_inView
    IniNumView ComboBox_CrossView
    
End Sub
Private Sub CheckBox_cross_view_Change()
    If CheckBox_cross_view.Value = True Then
        ComboBox_inView.Enabled = True
        ComboBox_CrossView.Enabled = True
    Else
        ComboBox_inView.Enabled = False
        ComboBox_CrossView.Enabled = False
    End If
End Sub
Private Sub IniNumView(mComboBox As ComboBox)
    Dim i As Integer
    
    mComboBox.Clear
    For i = 1 To 8
        If ActiveDesignFile.Views(i).IsOpen Then
            mComboBox.AddItem i
        End If
    Next i
End Sub
