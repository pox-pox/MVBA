Attribute VB_Name = "Module1"
Option Explicit

Declare Function mdlDialog_fileOpen Lib "stdmdlbltin.dll" (ByVal _
    fileName As String, ByVal rFileH As Long, ByVal _
    resourceId As Long, ByVal suggestedFileName As String, _
    ByVal filterString As String, ByVal defaultDirectory As String, _
    ByVal titleString As String) As Long
    
Public Type bPoint
    Name As String
    Point As Point3d
    Place As String
    Material As String
End Type

Public VKSPoint() As bPoint
Public mPoints() As Element

Sub Main()
    UserForm1.Show vbModeless
End Sub

Attribute VB_Name = "UserForm1"
Attribute VB_Base = "0{9E52857E-9C02-4DF6-ADE8-3808DDF98EE4}{9820B9D4-9C1A-411C-AA18-5FF07F47D7D9}"
Attribute VB_GlobalNameSpace = False
Attribute VB_Creatable = False
Attribute VB_PredeclaredId = True
Attribute VB_Exposed = False
Attribute VB_TemplateDerived = False
Attribute VB_Customizable = False
Option Explicit


Private Const attrId As Long = 22352
Private Const attrId1 As Long = 22353

Private Sub DrawPoint()
    Dim i As Long
    Dim mPoint As LineElement
    Dim sLink As TextElement
    Dim mLink As String
    
    For i = 0 To UBound(VKSPoint)
        Set mPoint = CreateLineElement2(Nothing, VKSPoint(i).Point, VKSPoint(i).Point)
        ActiveModelReference.AddElement mPoint
        mPoint.Level = CheckLevel(UserForm1.TextBox_LevelOfPoint)
        mLink = VKSPoint(i).Name & "|" & VKSPoint(i).Place & " " & AbbreviationMaterial(VKSPoint(i).Material)
        AddLinkage mPoint, mLink
        mPoint.Redraw
        If CheckBox_DrawAttribut.Value Then ' Подписать атрибуты
            AddLinkString mLink, VKSPoint(i).Point
        End If
    Next i
End Sub

Private Function AbbreviationMaterial(mMaterial As String) As String
    Select Case mMaterial
        Case "бетон"
            AbbreviationMaterial = "ж/б"
        Case "металлическая"
            AbbreviationMaterial = "мет."
        Case Else
            AbbreviationMaterial = "???"
    End Select
End Function

Private Sub AddLinkString(mLink As String, tPoint As Point3d)
    Dim mString As TextElement
    
    Set mString = CreateTextElement1(Nothing, mLink, tPoint, Matrix3dIdentity)
    mString.Level = CheckLevel(UserForm1.TextBox_LevelOfPoint)
    SetTextAtribut mString
    ActiveModelReference.AddElement mString
    mString.Redraw
    
End Sub
Private Sub DetectStationOffset()
    Dim mEnum As ElementEnumerator
    Dim mEnumAxis As ElementEnumerator
    Dim mFilterAxis As New ElementScanCriteria
    Dim mAxis As LineElement
    
    Dim prPoint As Point3d
    Dim i As Long
    Dim station As Double
    Dim offset As Double
    Dim newLink As String
    Dim vSegment As Vector3d
    Dim vOffset As Vector3d
    Dim moff As LineElement
    Dim vPlanar As Vector3d
    
    vPlanar = Vector3dFromXYZ(0, 0, 1)
    
    mFilterAxis.ExcludeAllLevels
    mFilterAxis.ExcludeAllTypes
    
    mFilterAxis.IncludeLevel ActiveDesignFile.Levels.Find(UserForm1.ComboBox_AxisLevel.Text)
    mFilterAxis.IncludeType msdElementTypeLineString
    
    Set mEnumAxis = ActiveModelReference.Scan(mFilterAxis)
    
    While mEnumAxis.MoveNext
        Set mAxis = mEnumAxis.Current.AsLineElement
    Wend
    
    If ActiveModelReference.AnyElementsSelected Then
        Set mEnum = ActiveModelReference.GetSelectedElements
        mPoints = mEnum.BuildArrayFromContents
        If mPoints.Type = msdElementTypeLine Then
            For i = 0 To UBound(mPoints)
                Project_Point1 mAxis, mPoints(i).AsLineElement.startPoint, prPoint, vSegment
                vOffset = Vector3dFromPoint3d(Point3dSubtract(mPoints(i).AsLineElement.startPoint, prPoint))
                SetElevation mAxis
                prPoint.Z = 0
                station = mAxis.DistanceAtPoint(prPoint)
                GetLinkage mPoints(i), newLink
                offset = Point3dDistanceXY(prPoint, mPoints(i).AsLineElement.startPoint)
                Set moff = CreateLineElement2(Nothing, prPoint, mPoints(i).AsLineElement.startPoint)
                moff.LineWeight = 0
                ActiveModelReference.AddElement moff
                moff.Redraw
                If Vector3dPlanarAngleBetweenVectors(vSegment, vOffset, vPlanar) > 0 Then
                    offset = -offset
                End If
                station = station + CDbl(TextBox_StartPiket_KM.Text) * 1000 + CDbl(TextBox_StartPiket_M.Text)
                Dim mLink As String
                mLink = GetNameAndPlaceFromLink(newLink) & "|" & "ПК " & station \ 100 & "+" & mRound(CDbl(station - (station \ 100) * 100), 3) & "|" & mRound(offset, 3)
                AddLinkage mPoints(i), mLink
                AddLinkString mLink, mPoints(i).AsLineElement.startPoint
            Next i
        End If
    End If
End Sub
Private Function GetNameAndPlaceFromLink(mLink As String) As String
    Dim Link() As String
    Link = Split(mLink, "|")
    GetNameAndPlaceFromLink = Link(0) & Link(1)
End Function
Private Function mRound(mNum As Double, r As Integer) As Double
  mRound = FormatNumber(Round(mNum, r), r, vbTrue, vbTrue, vbFalse)
End Function

Private Sub SetElevation(ByRef mElement As Element)
    mElement.Transform Transform3dFromMatrix3dPoint3d(Matrix3dFromScaleFactors(1, 1, 0), Point3dFromXYZ(0, 0, 0))
End Sub

Sub Project_Point1(mLine As Element, mPoint As Point3d, ByRef ProjPoint As Point3d, ByRef mVector As Vector3d)

Dim mComplexStr As ElementEnumerator
Dim i As Long
Dim j As Long
Dim minDist As Double
Dim tmpDist As Double
Dim tmpP As Point3d
Dim tl As LineElement

    Select Case mLine.Type
        Case msdElementTypeLineString
            minDist = 500000
                tmpP = mPoint
                i = mLine.AsLineElement.GetClosestSegment(tmpP)
                tmpP.Z = mLine.AsLineElement.Vertex(i + 1).Z * 0.5 + mLine.AsLineElement.Vertex(i + 2).Z * 0.5

                tmpDist = Dist_Segment_to_Point(mLine.AsLineElement.Vertex(i + 1), mLine.AsLineElement.Vertex(i + 2), tmpP)
                    If tmpDist < minDist Then
                        minDist = tmpDist
                        ProjPoint = Project_Point(mLine.AsLineElement.Vertex(i + 1), mLine.AsLineElement.Vertex(i + 2), tmpP)
                        mVector = Vector3dFromPoint3d(Point3dSubtract(mLine.AsLineElement.Vertex(i + 2), mLine.AsLineElement.Vertex(i + 1)))
                    End If
        Case msdElementTypeComplexString
            Set mComplexStr = mLine.AsComplexStringElement.GetSubElements
                minDist = 5000000
                While mComplexStr.MoveNext
                    Select Case mComplexStr.Current.Type
                        Case msdElementTypeLineString
                            tmpP = mPoint
                            i = mComplexStr.Current.AsLineElement.GetClosestSegment(tmpP)
                            tmpP.Z = mComplexStr.Current.AsLineElement.Vertex(i + 1).Z * 0.5 + mComplexStr.Current.AsLineElement.Vertex(i + 2).Z * 0.5
                            tmpDist = Dist_Segment_to_Point(mComplexStr.Current.AsLineElement.Vertex(i + 1), mComplexStr.Current.AsLineElement.Vertex(i + 2), tmpP)
                                If tmpDist < minDist Then
                                    minDist = tmpDist
                                    ProjPoint = Project_Point(mComplexStr.Current.AsLineElement.Vertex(i + 1), mComplexStr.Current.AsLineElement.Vertex(i + 2), tmpP)
                                    mVector = Vector3dFromPoint3d(Point3dSubtract(mLine.AsLineElement.Vertex(i + 2), mLine.AsLineElement.Vertex(i + 1)))
                                End If
                        Case msdElementTypeLine
                            tmpP = mPoint
                            tmpP.Z = mComplexStr.Current.AsLineElement.startPoint.Z
                            tmpDist = Dist_Segment_to_Point(mComplexStr.Current.AsLineElement.startPoint, mComplexStr.Current.AsLineElement.EndPoint, tmpP)
                                If tmpDist < minDist Then
                                minDist = tmpDist
                                ProjPoint = Project_Point(mComplexStr.Current.AsLineElement.startPoint, mComplexStr.Current.AsLineElement.EndPoint, tmpP)
                                mVector = Vector3dFromPoint3d(Point3dSubtract(mLine.AsLineElement.Vertex(i + 2), mLine.AsLineElement.Vertex(i + 1)))
                            End If
                    End Select
                Wend
    End Select
End Sub
Private Function Dist_Segment_to_Point(startPoint As Point3d, EndPoint As Point3d, iPoint As Point3d) As Double
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    Dim tmpL As LineElement
    vPoint = Vector3dSubtractPoint3dPoint3d(iPoint, startPoint)
    vLine = Vector3dSubtractPoint3dPoint3d(EndPoint, startPoint)
    
    c1 = Vector3dDotProduct(vPoint, vLine)
    c2 = Vector3dDotProduct(vLine, vLine)
        If c1 <= 0 Then
            Dist_Segment_to_Point = Point3dDistance(startPoint, iPoint)
        ElseIf c2 <= c1 Then
            Dist_Segment_to_Point = Point3dDistance(EndPoint, iPoint)
        Else
            k = c1 / c2
            vProject = Vector3dScale(vLine, k)
            pProject = Vector3dAdd(Vector3dFromPoint3d(startPoint), vProject)
            Dist_Segment_to_Point = Point3dDistance(Point3dFromVector3d(pProject), iPoint)
        End If
End Function
Private Function Project_Point(startPoint As Point3d, EndPoint As Point3d, iPoint As Point3d) As Point3d
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    
    vPoint = Vector3dSubtractPoint3dPoint3d(iPoint, startPoint)
    vLine = Vector3dSubtractPoint3dPoint3d(EndPoint, startPoint)
    
    c1 = Vector3dDotProduct(vPoint, vLine)
    c2 = Vector3dDotProduct(vLine, vLine)
        If c1 <= 0 Then
            Exit Function
'            Project_Point = startPoint
        ElseIf c2 <= c1 Then
            Exit Function
'            Project_Point = EndPoint
        Else
            k = c1 / c2
            vProject = Vector3dScale(vLine, k)
            Project_Point = Point3dFromVector3d(Vector3dAdd(Vector3dFromPoint3d(startPoint), vProject))
        End If
End Function

Private Sub SetTextAtribut(ByRef MText As TextElement)
    MText.TextStyle.Justification = msdTextJustificationLeftBottom
    MText.TextStyle.Height = 0.15
    MText.TextStyle.Width = 0.15
    MText.TextStyle.Font = ActiveDesignFile.Fonts("Arial")
    MText.LineWeight = 1
    MText.Color = 0
    'MText.Level = ActiveSettings.Level
End Sub
Private Sub LoadSettXLS()
    Dim strFName As String
    Dim lngfhandle As Long
    Dim lngrid As Long
    Dim retVal As Long
    Dim PathXls As String
    Dim myExcel As Excel.Application
    Dim myWorkbook As Excel.Workbook
    Dim CurrSheet As Worksheet
    Dim curRow As Long
    
    Set myExcel = CreateObject("Excel.Application")
    strFName = Space(255)
    Erase VKSPoint
    
    curRow = 2 ' Начинать поиск со сторой строки
    retVal = mdlDialog_fileOpen(strFName, lngfhandle, lngrid, "", "*.xlsx", _
                                ActiveDesignFile.Path, "Открыть файл Specification")
    Select Case retVal
        Case 0 'Open
            PathXls = Left(strFName, InStr(1, strFName, Chr(0)) - 1)
            
            Set myWorkbook = myExcel.Workbooks.Open(PathXls)
            Set CurrSheet = myWorkbook.Worksheets(1)
                While Not (CurrSheet.Cells(curRow, 1) = "")
                    If CurrSheet.Cells(curRow, 1) <> "" And CurrSheet.Cells(curRow, 2) <> "" Then
                        RedimPreserve VKSPoint
                        VKSPoint(UBound(VKSPoint)).Name = CurrSheet.Cells(curRow, 1)
                        VKSPoint(UBound(VKSPoint)).Point.X = CDbl(CurrSheet.Cells(curRow, 5))
                        VKSPoint(UBound(VKSPoint)).Point.Y = CDbl(CurrSheet.Cells(curRow, 4))
                        VKSPoint(UBound(VKSPoint)).Point.Z = CDbl(CurrSheet.Cells(curRow, 6))
                        VKSPoint(UBound(VKSPoint)).Place = CurrSheet.Cells(curRow, 2)
                        VKSPoint(UBound(VKSPoint)).Material = CurrSheet.Cells(curRow, 3)
                    End If
                    curRow = curRow + 1
                Wend
            MsgBox "Файл Specification загружен:" & vbCr & strFName
        Case 1 'Cancel
            MsgBox "Файл не выделен"
    End Select
    myExcel.Quit
End Sub
Sub RedimPreserve(ByRef mB() As bPoint)
    Dim i As Long
    On Error Resume Next
    i = UBound(mB) + 1
    If Err.Number = 9 Then
        ReDim mB(0)
    Else: ReDim Preserve mB(i)
    End If
    Err.Clear
End Sub
Function CheckLevel(LevelName As String) As Level
    Dim myLevel As Level
    On Error Resume Next
    
    Set CheckLevel = ActiveDesignFile.Levels(LevelName)
    If Err.Number <> 0 And LevelName <> "" Then
         Set myLevel = ActiveDesignFile.AddNewLevel(LevelName)
         myLevel.ElementLineWeight = 8
         
         ActiveDesignFile.Levels.Rewrite
         MsgBox "Создан слой: " & LevelName
         Set CheckLevel = myLevel
    End If
    Err.Clear
End Function
Sub AddLinkage(MyEle As Element, mLink As String)
    Dim Link As String
    DeleteAttributes MyEle
    'Link = Attribut & "@" & Description
    AddStringAttribute MyEle, mLink
End Sub
Sub DeleteAttributes(ele As Element)
    Dim dblk() As DataBlock
    Dim index As Integer
    
    dblk = ele.GetUserAttributeData(attrId)
    For index = LBound(dblk) To UBound(dblk)
        ele.DeleteUserAttributeData attrId, index
        ele.Rewrite
    Next
End Sub
Sub AddStringAttribute(ele As Element, str As String)
    Dim dblk As New DataBlock
    
    dblk.CopyString str, True
    ele.AddUserAttributeData attrId, dblk
    ele.Rewrite
End Sub
Sub GetLinkage(MyEle As Element, mLink As String)
    Dim dblk() As DataBlock
    Dim Link As String
    Dim Links() As String
    Dim index As Integer
    
        dblk = MyEle.GetUserAttributeData(attrId)
        For index = LBound(dblk) To UBound(dblk)
            dblk(index).offset = 0
            dblk(index).CopyString Link, False
        Next
    If UBound(dblk) >= 0 Then
        dblk = MyEle.GetUserAttributeData(attrId)
        dblk(0).CopyString mLink, False
    Else
        mLink = ""
    End If
End Sub

Private Sub CommandButton_CalculateStation_Click()
    DetectStationOffset
End Sub

Private Sub CommandButton_CreateReport_Click()
    ExportToExcel mPoints
End Sub

Private Sub CommandButton_DrawPoints_Click()
    DrawPoint
End Sub

Private Sub CommandButton_LoadPointFromXLS_Click()
    LoadSettXLS
End Sub

Private Sub InitializeLevels(mComboBox As ComboBox)
  Dim myLevel As Level

  mComboBox.Clear
  For Each myLevel In ActiveDesignFile.Levels
    mComboBox.AddItem myLevel.Name
  Next
End Sub
Private Sub UserForm_Initialize()
    InitializeLevels ComboBox_AxisLevel
End Sub

Private Sub ExportToExcel(mPoints() As Element)
' ---------Excel Application, workbook, and sheet object
    Dim xlApp As Excel.Application
    Dim xlBook As Excel.Workbook
    Dim xlSheet As Object
' -------- Filename
    Dim fileDoesExist As Boolean
    Dim fileName As String
' ---------Create Excel Application
    Dim i As Long
    Dim Attribut As String
    Dim Description As String
    Dim rPoints() As Element
    Dim mEnum As ElementEnumerator
    
    Set xlApp = CreateObject("Excel.Application")
    xlApp.Visible = False
    fileName = "CatalogOfSurveyPoints.xlsx"
    fileDoesExist = Dir("d:\" & fileName) > ""
    Set xlBook = xlApp.Workbooks.Add
    Set xlSheet = xlBook.Sheets(1)
' -----------Блок для записи ячеек
    TablePointsHeader xlSheet ' Формирование шапки таблицы
    For i = 0 To UBound(mPoints)
        If mPoints(i).Type = msdElementTypeLine Then
            Dim Link As String
            GetLinkage mPoints(i), Link
            Dim Links() As String
            Links = Split(Link, "|")
            xlSheet.Cells(i + 5, 1) = Links(0)
            xlSheet.Cells(i + 5, 2) = Links(2)
            If CDbl(Links(3)) > 0 Then
                xlSheet.Cells(i + 5, 4) = mRound(CDbl(Links(3)), 3)
            Else
                xlSheet.Cells(i + 5, 3) = -mRound(CDbl(Links(3)), 3)
            End If
            xlSheet.Cells(i + 5, 5) = "АО " & Chr(34) & "ТПС" & Chr(34)
            xlSheet.Cells(i + 5, 6) = Links(1)
            xlSheet.Cells(i + 5, 7) = myRound(CDbl(mPoints(i).AsLineElement.startPoint.Z))
            xlSheet.Columns("A:G").AutoFit
            xlSheet.Columns("A:G").HorizontalAlignment = xlCenter
        End If
    Next i
'    Dim index As Integer
'    On Error Resume Next
'    While Dir(ActiveDesignFile.Path & "\" & "Table_1_" & index & ".xlsx") > ""
'        index = index + 1
'    Wend
    xlBook.SaveAs fileName:=ActiveDesignFile.Path & "\" & "Table_1_" & ComboBox_AxisLevel.Text & ".xlsx"
    xlBook.Save
    xlApp.Quit
    MsgBox "Отчет сформирован: " & ActiveDesignFile.Path & "\" & "Table_1_" & ComboBox_AxisLevel.Text & ".xlsx"
End Sub
Function myRound(Value As Double) As String
    myRound = FormatNumber(Round(Value, CInt(3)), CInt(3), vbTrue, vbFalse, vbTrue)
End Function

Private Sub TablePointsHeader(mSheet As Object)
    mSheet.Cells(1, 1) = "Наименование знаков"
    mSheet.Cells(1, 2) = "Местоположение знаков"
    mSheet.Cells(1, 5) = "Организация, заложившая знак"
    mSheet.Cells(1, 6) = "Описание марок и реперов"
    mSheet.Cells(1, 7) = "Отметка (Балтийская система высот)"
    mSheet.Cells(2, 2) = "км, пк, +"
    mSheet.Cells(2, 3) = "От оси пути"
    mSheet.Cells(3, 3) = "Лево"
    mSheet.Cells(3, 4) = "Право"
    mSheet.Cells(4, 1) = ComboBox_AxisLevel.Text
    
    mSheet.Range(mSheet.Cells(1, 1), mSheet.Cells(3, 1)).Merge
    mSheet.Range(mSheet.Cells(1, 2), mSheet.Cells(1, 4)).Merge
    mSheet.Range(mSheet.Cells(2, 2), mSheet.Cells(3, 2)).Merge
    mSheet.Range(mSheet.Cells(2, 3), mSheet.Cells(2, 4)).Merge
    mSheet.Range(mSheet.Cells(1, 5), mSheet.Cells(3, 5)).Merge
    mSheet.Range(mSheet.Cells(1, 6), mSheet.Cells(3, 6)).Merge
    mSheet.Range(mSheet.Cells(1, 7), mSheet.Cells(3, 7)).Merge
    mSheet.Range(mSheet.Cells(1, 1), mSheet.Cells(3, 7)).WrapText = True
    mSheet.Range(mSheet.Cells(4, 1), mSheet.Cells(4, 7)).Merge
    
    mSheet.Range(mSheet.Cells(1, 1), mSheet.Cells(3, 7)).HorizontalAlignment = xlCenter
    mSheet.Range(mSheet.Cells(1, 1), mSheet.Cells(3, 7)).VerticalAlignment = xlCenter
    mSheet.Columns("A:F").AutoFit
End Sub
