Attribute VB_Name = "GetPictureCell"
Option Explicit

Sub DrawCellPreview(CellName As String)
    Dim width As Long
    Dim height As Long
    Dim MyCell As CellElement
    Dim MyMatrix As Matrix3d
    Dim MyTransform As Transform3d
    Dim Op As Point3d
    On Error Resume Next
                    width = PointsToPixelsX(MyForm.CellPreview.width)
                    height = PointsToPixelsY(MyForm.CellPreview.height)
                    If CellName <> "" Then
                            MyMatrix = Matrix3dFromAxisAndRotationAngle(0, Pi / 2)
                            Set MyCell = CreateCellElement3(CellName, Op, True)
                            
                            Set MyForm.CellPreview.Picture = MyCell.GetPicture(width * 0.77, height * 0.77, True)
                            MyTransform = Transform3dFromMatrix3dPoint3d(MyMatrix, MyCell.origin)
                            MyCell.transform MyTransform
                            Set MyForm.CellPreviewTop.Picture = MyCell.GetPicture(width * 0.37, height * 0.37, True)
                            
                            MyMatrix = Matrix3dFromMatrix3dTimesMatrix3d(MyMatrix, Matrix3dFromAxisAndRotationAngle(1, Pi / 4))
                            MyMatrix = Matrix3dFromMatrix3dTimesMatrix3d(MyMatrix, Matrix3dFromAxisAndRotationAngle(2, Pi / 4))
                            MyTransform = Transform3dFromMatrix3dPoint3d(MyMatrix, MyCell.origin)
                            MyCell.transform MyTransform
                            Set MyForm.CellPreviewTop45.Picture = MyCell.GetPicture(width * 0.37, height * 0.37, True)
                    End If
    Resume
End Sub

Attribute VB_Name = "LCE_CreateArrow"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private stPoint As Point3d 'Главная точка опоры, начальная точка установки стрелок
Private retPoint As Point3d ' Точка для возвратной стрелки
Private retBoolean As Boolean ' Условие для указания первого cell

Implements ILocateCommandEvents

Private Sub ILocateCommandEvents_Accept(ByVal Element As Element, Point As Point3d, ByVal View As View)
    Dim arrowCell As CellElement
    Dim oPoint As Point3d ' ответная точка
    Dim RotationMatrix As Matrix3d
    Dim Sc As Point3d
    Sc.X = 1
    Sc.Y = 1
    Sc.Z = 1
    RotationMatrix = Matrix3dFromAxisAndRotationAngle(2, MyModule.AngleTxt(stPoint, Point))
    Set arrowCell = CreateCellElement2(MyForm.cmbCell.Text, stPoint, Sc, True, RotationMatrix)
    arrowCell.Level = ActiveDesignFile.Levels.find(ActiveSettings.Level.Name)
    ActiveModelReference.AddElement arrowCell
    arrowCell.Redraw
    retPoint = stPoint
End Sub
Private Sub ILocateCommandEvents_Cleanup()

End Sub

Private Sub ILocateCommandEvents_Dynamics(Point As Point3d, ByVal View As View, ByVal DrawMode As MsdDrawingMode)
    Dim arrowCell As CellElement
    Dim RotationMatrix As Matrix3d
    Dim Sc As Point3d
    Sc.X = 1
    Sc.Y = 1
    Sc.Z = 1
    RotationMatrix = Matrix3dFromAxisAndRotationAngle(2, MyModule.AngleTxt(stPoint, Point))
    Set arrowCell = CreateCellElement2(MyForm.cmbCell.Text, stPoint, Sc, True, RotationMatrix)
    arrowCell.Redraw DrawMode
End Sub

Private Sub ILocateCommandEvents_LocateFailed()
    CommandState.StartLocate Me
End Sub

Private Sub ILocateCommandEvents_LocateFilter(ByVal Element As Element, Point As Point3d, Accepted As Boolean)
   Dim MyCell As CellElement
   Accepted = False
   Dim arrowCell As CellElement
   Dim tarCell As CellElement ' Cell
   Dim oPoint As Point3d ' ответная точка
   Dim RotationMatrix As Matrix3d
   Dim Sc As Point3d
   Sc.X = 1
   Sc.Y = 1
   Sc.Z = 1
    
   Set tarCell = Element

   If Element.IsCellElement = True Then
        Set MyCell = Element
        Accepted = True
        stPoint = MyCell.origin
        ShowCommand "Стрелки на опоре"
        If retBoolean = True And tarCell.Name <> MyForm.cmbCell.Text Then
            Set tarCell = Element
            RotationMatrix = Matrix3dFromAxisAndRotationAngle(2, MyModule.AngleTxt(stPoint, retPoint))
            Set arrowCell = CreateCellElement2(MyForm.cmbCell.Text, stPoint, Sc, True, RotationMatrix)
            arrowCell.Level = ActiveDesignFile.Levels.find(ActiveSettings.Level.Name)
            ActiveModelReference.AddElement arrowCell
            arrowCell.Redraw
        End If
        CommandState.StartDynamics
        retBoolean = True
    End If
End Sub

Private Sub ILocateCommandEvents_LocateReset()
    CommandState.StartDefaultCommand
End Sub

Private Sub ILocateCommandEvents_Start()
    CommandState.EnableAccuSnap
End Sub

Attribute VB_Name = "MyForm"
Attribute VB_Base = "0{AB1098D3-7822-4863-8F8F-A179DDAA0DE0}{B2BACABD-BFCD-4C89-BB62-B929E8E0BB25}"
Attribute VB_GlobalNameSpace = False
Attribute VB_Creatable = False
Attribute VB_PredeclaredId = True
Attribute VB_Exposed = False
Attribute VB_TemplateDerived = False
Attribute VB_Customizable = False
Option Explicit
Private Const attrId As Long = 22352
Private Sub cmbPArrow_Click()
    CommandState.StartLocate New LCE_CreateArrow
End Sub

Private Sub CheckBox_cross_view_Change()
    If CheckBox_cross_view.Value = True Then
        ComboBox_inView.Enabled = True
        ComboBox_CrossView.Enabled = True
    Else
        ComboBox_inView.Enabled = False
        ComboBox_CrossView.Enabled = False
    End If
End Sub


Private Sub cmbCell_Change()
    GetPictureCell.DrawCellPreview MyForm.cmbCell.Text
End Sub
Private Sub cmbCell_DblClick(ByVal Cancel As MSForms.ReturnBoolean)
    UserForm_Initialize
End Sub
Private Sub cmpPlace_Click()
    mCellName = cmbCell.Text
    CommandState.StartPrimitive New PCE_PlaceCellRotate, True
End Sub
Private Sub cmbCell_MouseDown(ByVal Button As Integer, ByVal Shift As Integer, ByVal X As Single, ByVal Y As Single)
    GetPictureCell.DrawCellPreview MyForm.cmbCell.Text
End Sub
Private Sub cmbCell2_Change()
    GetPictureCell.DrawCellPreview MyForm.cmbCell2.Text
End Sub
Private Sub cmbCell2_MouseDown(ByVal Button As Integer, ByVal Shift As Integer, ByVal X As Single, ByVal Y As Single)
     GetPictureCell.DrawCellPreview MyForm.cmbCell2.Text
End Sub
Private Sub cmpPlace2_Click()
    mCellName = cmbCell2.Text
    CommandState.StartPrimitive New PCE_PlaceCellRotate, True
End Sub
Private Sub cmbCell3_Change()
    GetPictureCell.DrawCellPreview MyForm.cmbCell3.Text
End Sub
Private Sub cmbCell3_MouseDown(ByVal Button As Integer, ByVal Shift As Integer, ByVal X As Single, ByVal Y As Single)
     GetPictureCell.DrawCellPreview MyForm.cmbCell3.Text
End Sub
Private Sub cmpPlace3_Click()
    mCellName = cmbCell3.Text
    CommandState.StartPrimitive New PCE_PlaceCellRotate, True
End Sub
Private Sub ComboBox_CrossView_DblClick(ByVal Cancel As MSForms.ReturnBoolean)
    UserForm_Initialize
End Sub
Private Sub ComboBox_inView_DblClick(ByVal Cancel As MSForms.ReturnBoolean)
    UserForm_Initialize
End Sub

Private Sub CommandButton_openXLS_Click()
    LoadLayout
End Sub

Private Sub CommandButton_ToClipboard_Click()
    Dim MyData As DataObject
    Set MyData = New DataObject
    
        If IsCellLibraryAttached Then
            '  List the names of all of the cells that are
            '  eligible to be the active cell.
            Dim oCIE As CellInformationEnumerator
            Dim OCellInfo As CellInformation
            '  Do not include shared cells, but include everything
            '  in the MS_CELLLIST
            Set oCIE = GetCellInformationEnumerator(True, True)
            Do While oCIE.MoveNext
                Dim message As String
                Set OCellInfo = oCIE.Current
                With OCellInfo
                    message = message & .Name & vbTab
                    message = message & .Description & vbCrLf
                End With
            Loop
        End If
    MyData.SetText message
    MyData.PutInClipboard ' Копирование в буфер обмена
End Sub

Private Sub ListBox_cellName_Change()
        If isInAttach(ListBox_cellName.Text) Then
            GetPictureCell.DrawCellPreview ListBox_cellName.Text
            GetDescription ListBox_cellName.Text
'        ElseIf ListBox_cellName.Text <> "" Then
'            MsgBox "Cell в библиотеке не найден", vbOKOnly
        End If
End Sub

Private Function GetDescription(nCell As String)
    Dim i As Long
    
    For i = 0 To UBound(mLayout)
        If mLayout(i).nCell = nCell Then
            Label_Description.Caption = mLayout(i).Description
            Exit For
        Else
            Label_Description.Caption = ""
        End If
    Next i
End Function

Private Sub ListBox_cellName_DblClick(ByVal Cancel As MSForms.ReturnBoolean)
    If isInAttach(ListBox_cellName.Text) Then
        mCellName = ListBox_cellName.Text
        CommandState.StartPrimitive New PCE_PlaceCellRotate, True
'    ElseIf ListBox_cellName.Text <> "" Then
'        MsgBox "Указанный Cell в библиотеке не найден!", vbOKOnly
    End If
End Sub

Private Function isInAttach(cName As String) As Boolean
    Dim MyCellEnum As CellInformationEnumerator
    Dim MyCell As CellInformation
    Dim find As Boolean
    find = False
            If IsCellLibraryAttached Then
               Set MyCellEnum = Application.GetCellInformationEnumerator(False, False)
                   While MyCellEnum.MoveNext
                       Set MyCell = MyCellEnum.Current
                       If cName = MyCell.Name Then
                           find = True
                       End If
                   Wend
            Else: MsgBox "Библиотека Cell не подключена", vbOKOnly
        End If
    If find = False And cName <> "" Then MsgBox "Cell в библиотеке не найден", vbOKOnly
    isInAttach = find
End Function

Private Sub ListBox_group_Change()
    changeGroup ListBox_group.Text
End Sub


Private Sub UserForm_Initialize()
    Dim MyCellEnum As CellInformationEnumerator
    Dim MyCell As CellInformation
    If IsCellLibraryAttached Then
    cmbCell.Clear
    cmbCell2.Clear
    cmbCell3.Clear
            Set MyCellEnum = Application.GetCellInformationEnumerator(False, False)
            While MyCellEnum.MoveNext
                Set MyCell = MyCellEnum.Current
                cmbCell.AddItem MyCell.Name
                cmbCell2.AddItem MyCell.Name
                cmbCell3.AddItem MyCell.Name
            Wend
        Else: MsgBox "Библиотека Cell не подключена", vbOKOnly
    End If
    IniNumView ComboBox_inView
    IniNumView ComboBox_CrossView
    
End Sub
Private Sub IniNumView(mComboBox As ComboBox)
    Dim i As Integer
    
    mComboBox.Clear
    For i = 1 To 8
        If ActiveDesignFile.Views(i).IsOpen Then
            mComboBox.AddItem i
        End If
    Next i
End Sub

Private Sub LoadLayout() ' Загрузка схемы XLS
    Dim strFName As String
    Dim lngfhandle As Long
    Dim lngrid As Long
    Dim retVal As Long
    Dim PathXls As String
    Dim myExcel As Excel.Application
    Dim myWorkbook As Excel.Workbook
    Dim CurrSheet As Worksheet
    Dim curRow  As Long
    Set myExcel = CreateObject("Excel.Application")
    strFName = Space(255)
    ReDim mLayout(0)
    curRow = 1
    retVal = mdlDialog_fileOpen(strFName, lngfhandle, lngrid, "", "*.xls", _
                                    ActiveDesignFile.Path, "Открыть файл-схему")
                                    
    Select Case retVal
        Case 0 'Open
            PathXls = Left(strFName, InStr(1, strFName, Chr(0)) - 1)
            MsgBox "Схема загружена:" & vbCr & strFName
            Set myWorkbook = myExcel.Workbooks.Open(PathXls)
         '  Set myExcel = Nothing
            Set CurrSheet = myWorkbook.Worksheets(1)
                While Not CurrSheet.Cells(curRow, 2) = ""
                    ReDim Preserve mLayout(curRow - 1)
                    With mLayout(UBound(mLayout))
                        .group = CurrSheet.Cells(curRow, 1)
                        .nCell = CurrSheet.Cells(curRow, 2)
                        .Description = CurrSheet.Cells(curRow, 3)
                    End With
                    curRow = curRow + 1
                    
                Wend
        Case 1 'Cancel
            MsgBox "Файл не выделен"
    End Select
    myExcel.Quit
    fillGroup
End Sub

Private Sub fillGroup()
Dim i  As Long
Dim j As Long

    ListBox_group.Clear
    ListBox_group.AddItem mLayout(0).group
    For i = 1 To UBound(mLayout)
        For j = 0 To ListBox_group.ListCount - 1
            If ListBox_group.List(j) = mLayout(i).group Then
                Exit For
            ElseIf j = ListBox_group.ListCount - 1 Then
                ListBox_group.AddItem mLayout(i).group
            End If
        Next j
    Next i
End Sub

Private Sub changeGroup(group As String)
    Dim i As Long
    ListBox_cellName.Clear
    
    For i = 0 To UBound(mLayout)
        If mLayout(i).group = group Then
            ListBox_cellName.AddItem mLayout(i).nCell
        End If
    Next i
    
End Sub

Attribute VB_Name = "MyModule"
Option Explicit
Declare Function mdlDialog_fileOpen Lib "stdmdlbltin.dll" (ByVal _
    fileName As String, ByVal rFileH As Long, ByVal _
    resourceId As Long, ByVal suggestedFileName As String, _
    ByVal filterString As String, ByVal defaultDirectory As String, _
    ByVal titleString As String) As Long
Public Reset As Boolean
Public PTstart As Point3d
Public PTend As Point3d
Public ID As Integer
Public mCellName As String

Public Type Layout
    group As String
    nCell As String
    Description As String
End Type
Public mLayout() As Layout

'
'Public Sub GetXYZ()
'    Dim myCIQ As CadInputQueue
'    Dim myCIM As CadInputMessage
'    Set myCIQ = CadInputQueue
'    Reset = False
'    'ShowCommand "Нанесение текста"
'    'ShowPrompt "Укажите начальную точку"
'    Set myCIM = myCIQ.GetInput(msdCadInputTypeDataPoint, msdCadInputTypeReset)
'        Select Case myCIM.InputType
'            Case msdCadInputTypeReset
'                Exit Sub
'            Case msdCadInputTypeDataPoint
'                PTstart = myCIM.Point
'        End Select
'    CadInputQueue.SendCommand "PLACE Line"
'    CadInputQueue.SendDataPoint PTstart
'    'ShowCommand "Нанесение текста"
'    'ShowPrompt "Укажите конечную точку"
'    Set myCIM = myCIQ.GetInput
'        Select Case myCIM.InputType
'            Case msdCadInputTypeReset
'                Reset = True
'                Exit Sub
'            Case msdCadInputTypeDataPoint
'                PTend = myCIM.Point
'        End Select
'End Sub
Sub main()
    MyForm.Show vbModeless
End Sub
Function AngleTxt(pSt As Point3d, pEnd As Point3d) As Double
Dim dAng As Double
Dim Angel As Double
Dim ang As Double
Dim dx As Double
Dim dy As Double
dx = pEnd.X - pSt.X
dy = pEnd.Y - pSt.Y
If dy <> 0 Then
    ang = Atn(dx / dy)
    If dx >= 0 And dy > 0 Then
        dAng = ang
    ElseIf dx >= 0 And dy < 0 Then
        dAng = ang + Pi
    ElseIf dx < 0 And dy < 0 Then
        dAng = ang + Pi
    ElseIf dx < 0 And dy > 0 Then
        dAng = ang + 2 * Pi
    End If
ElseIf dy = 0 Then

    If dx > 0 Then
        dAng = Pi / 2
    ElseIf dx < 0 Then
        dAng = 3 * Pi / 4
    End If
End If
Angel = Pi / 2 - dAng
AngleTxt = Angel
End Function

Attribute VB_Name = "PCE_PlaceCellRotate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private bPoint          As Point3d ' Точка вставки Cell
Private fdPoint         As Point3d '
Private FirstPoint      As Boolean ' Проверка на первую точку
Private Second          As Boolean
Private moveCell        As Boolean
Private CellName        As String
Private MyCell          As CellElement
Private prPointOnPlan   As Point3d
Private rotation        As Matrix3d
Private dRotation       As Matrix3d
Implements IPrimitiveCommandEvents
Private Sub IPrimitiveCommandEvents_Cleanup()
End Sub

Private Sub IPrimitiveCommandEvents_DataPoint(Point As Point3d, ByVal View As View)
Dim tmpCell         As CellElement
Dim rotation        As Matrix3d
Dim RotationMatrix  As Matrix3d
Dim OriginAccu      As Point3d
Dim oClone          As Element

Dim origin          As LineElement

    If FirstPoint = False And Second = False Then
        bPoint = Point
        FirstPoint = True
            If MyForm.CheckBox_cross_view.Value = True Then
                CrossSection CInt(MyForm.ComboBox_inView.Text), CInt(MyForm.ComboBox_CrossView.Text)
            End If
    ElseIf FirstPoint = True Then
        dRotation = Matrix3dInverse(View.rotation)
        Set MyCell = CreateCellElement2(mCellName, bPoint, Point3dOne, True, dRotation)
        MyCell.transform SecondRotate(View, Point)
        ActiveModelReference.AddElement MyCell
        MyCell.Redraw
        Second = True
        moveCell = True
        FirstPoint = False
        fdPoint = Point
    ElseIf moveCell = True Then
            MyCell.Redraw msdDrawingModeTemporaryErase
            MyCell.Move Point3dSubtract(ActiveDepthDraw(View, bPoint, Point), bPoint)
            MyCell.Redraw msdDrawingModeNormal
            MyCell.Rewrite
            fdPoint = Point3dAddPoint3dVector3d(fdPoint, Vector3dSubtractPoint3dPoint3d(ActiveDepthDraw(View, bPoint, Point), bPoint))
            bPoint = ActiveDepthDraw(View, bPoint, Point)
            moveCell = False
    ElseIf Second = True Then
        Set tmpCell = ActiveModelReference.GraphicalElementCache.GetLastValidElement.AsCellElement
        ActiveModelReference.RemoveElement tmpCell
        tmpCell.Redraw
        Set MyCell = CreateCellElement2(mCellName, bPoint, Point3dOne, True, dRotation)
        MyCell.transform SecondRotate(View, ActiveDepthDraw(View, bPoint, Point))
        ActiveModelReference.AddElement MyCell
        MyCell.Redraw
    End If

End Sub

Private Sub IPrimitiveCommandEvents_Dynamics(Point As Point3d, ByVal View As View, ByVal DrawMode As MsdDrawingMode)
    Dim transform As Transform3d
    Dim RotationMatrix As Matrix3d
    Dim oClone          As Element
    
        If FirstPoint = False And Second = False Then
            rotation = Matrix3dInverse(View.rotation)
            transform = Transform3dFromMatrix3dAndFixedPoint3d(rotation, Point)
            Set MyCell = CreateCellElement2(mCellName, Point, Point3dOne, True, Matrix3dIdentity)
            MyCell.transform transform
            MyCell.Redraw DrawMode
        ElseIf moveCell = True Then
            Set oClone = MyCell.Clone
            oClone.Redraw msdDrawingModeTemporaryErase
            oClone.Move Point3dSubtract(ActiveDepthDraw(View, bPoint, Point), bPoint)
            oClone.Redraw DrawMode
        ElseIf FirstPoint = True Then
            rotation = Matrix3dInverse(View.rotation)
            Set MyCell = CreateCellElement2(mCellName, bPoint, Point3dOne, True, rotation)
            MyCell.transform SecondRotate(View, Point)
            MyCell.Redraw DrawMode
        ElseIf FirstPoint = False And Second = True Then '  Крайний поворот
            Set MyCell = CreateCellElement2(mCellName, bPoint, Point3dOne, True, rotation)
            MyCell.transform SecondRotate(View, ActiveDepthDraw(View, bPoint, Point))
            MyCell.Redraw DrawMode
        
        End If
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
    CommandState.AccuDrawHints.Deactivate
    CommandState.StartDynamics
    
    FirstPoint = False
        If MyForm.CheckBox_cross_view.Value = True Then
            CrossSection CInt(MyForm.ComboBox_inView.Text), CInt(MyForm.ComboBox_CrossView.Text)
        End If
End Sub
Function Point3dToString(pnt As Point3d, myLable As Label) As String
    With pnt
        myLable.Caption = "X= " & Round(.X, 2) & vbCrLf & "Y= " & Round(.Y, 2) & vbCrLf & "Z= " & Round(.Z, 2)
    End With
End Function

Function SecondRotate(dView As View, rotPoint As Point3d) As Transform3d
    Dim plan        As Plane3d
    
    Dim myRot       As Matrix3d
    Dim pntTemp     As Point3d
    Dim PerpVector  As Vector3d
    Dim tmpVector   As Vector3d
    Dim prBpoint    As Point3d
    
    If FirstPoint = True And Second = False Then
        With fdPoint
            .X = bPoint.X
            .Y = bPoint.Y
            .Z = 0
        End With
    End If
    
    prBpoint = bPoint
    prBpoint.Z = 0
    
    plan.origin = fdPoint
    plan.Normal = dView.rotation.RowZ
    
    If fdPoint.X <> bPoint.X And fdPoint.Y <> bPoint.Y Then
        plan.Normal = Point3dFromVector3d(Vector3dCrossProduct(Vector3dUnitPerpendicularXY(Vector3dFromPoint3d(Point3dSubtract(fdPoint, bPoint))), Vector3dSubtractPoint3dPoint3d(fdPoint, bPoint)))
    End If
    prPointOnPlan = Point3dProjectToPlane3d(rotPoint, plan)
    myRot = Matrix3dFromRotationBetweenVectors(Point3dSubtract(prBpoint, bPoint), Point3dSubtract(prPointOnPlan, bPoint))
    SecondRotate = Transform3dFromMatrix3dAndFixedPoint3d(myRot, bPoint)
    
End Function

Function ActiveDepthDraw(mView As View, aPoint As Point3d, tPoint As Point3d) As Point3d
    Dim mPlan         As Plane3d
    
    With mPlan
        .origin = aPoint
        .Normal = mView.rotation.RowZ
    End With
        ActiveDepthDraw = Point3dProjectToPlane3d(tPoint, mPlan)
End Function

Private Sub CrossSection(inV As Integer, crossV As Integer)
    Dim inView      As View
    Dim crossView   As View
    
    Dim origin      As LineElement
    Dim pP          As Point3d
    Dim pCenter     As Point3d
    
    
    Set inView = ActiveDesignFile.Views(inV)
    Set crossView = ActiveDesignFile.Views(crossV)
     
    
    crossView.SetArea Point3dAddPoint3dVector3d(inView.Center, Vector3dRotateXY(Vector3dSubtractPoint3dPoint3d(inView.origin, inView.Center), -Pi / 2)), inView.Extents, Matrix3dFromMatrix3dTimesMatrix3d(inView.rotation, Matrix3dFromAxisAndRotationAngle(2, Pi / 2)), inView.ActiveDepth
    crossView.Center = inView.Center
   ' crossView.SetClippingDistanceFromGlobalOrigin 0, 10
   ' CommandState.AccuDrawHints.SetOrigin inView.Center
    crossView.Redraw

'    Set origin = CreateLineElement2(Nothing, bPoint, bPoint)
'    origin.LineWeight = 10
'    origin.Color = 4
'    ActiveModelReference.AddElement origin
'    origin.Redraw
'
'    Set origin = CreateLineElement2(Nothing, crossView.Center, crossView.Center)
'    origin.LineWeight = 12
'    origin.Color = 7
'    ActiveModelReference.AddElement origin
'    origin.Redraw
'
'    Set origin = CreateLineElement2(Nothing, crossView.origin, crossView.origin)
'    origin.LineWeight = 12
'    origin.Color = 2
'    ActiveModelReference.AddElement origin
'    origin.Redraw
'
'    Set origin = CreateLineElement2(Nothing, inView.origin, inView.origin)
'    origin.LineWeight = 12
'    origin.Color = 3
'    ActiveModelReference.AddElement origin
'    origin.Redraw
End Sub
