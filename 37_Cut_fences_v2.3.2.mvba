Attribute VB_Name = "Module1"
Option Explicit

Private Type BrowseInfo
    hWndOwner As Long
    pidlRoot As Long
    sDisplayName As String
    sTitle As String
    ulFlags As Long
    lpfn As Long
    lParam As Long
    iImage As Long
End Type

Private Declare Function SHBrowseForFolder Lib "shell32.dll" (bBrowse As BrowseInfo) As Long
Private Declare Function SHGetPathFromIDList Lib "shell32.dll" (ByVal Item As Long, ByVal sDir As String) As Long

Private Const Bif_ReturnOnlyFSDirs = 1
Private Const Bif_DontGoBelowDomain = 2
Private Const Bif_EditBox = 16
Private Const Bif_NewDialogStyle = 64
Private Const Bif_UseNewui = 80
Private Const Bif_BrowseForComputer = 4096
Private Const Bif_BrowseForPrinter = 8192
Private Const Bif_BrowseIncludeFiles = 16384

Declare Function mdlDialog_fileOpen Lib "stdmdlbltin.dll" (ByVal _
    fileName As String, ByVal rFileH As Long, ByVal _
    resourceId As Long, ByVal suggestedFileName As String, _
    ByVal filterString As String, ByVal defaultDirectory As String, _
    ByVal titleString As String) As Long
Public dgntmpName As String
Public PathDGN As String
Public CuttingFilesPath() As String

Public Sub Select_temp()
    Dim strFName As String
    Dim lngfhandle As Long
    Dim lngrid As Long
    Dim retVal As Long
    strFName = Space(255)
    retVal = mdlDialog_fileOpen(strFName, lngfhandle, lngrid, "", "*.dgn", _
                                    ActiveDesignFile.Path, "Выбрать шаблон DGN")
    dgntmpName = Left(strFName, InStr(1, strFName, Chr(0)) - 1)
    UserForm1.Label_TargetFolder.Caption = Left(dgntmpName, InStrRev(dgntmpName, "\"))
End Sub

Public Sub SelectFolder()
    Dim MyBI As BrowseInfo
    Dim FList As Long
    Dim DirName As String
    Dim SelFolder As Long
    DirName = Space(255)
    
    MyBI.sTitle = "Выбрать папку с файлами:"
    MyBI.sDisplayName = Space(255)
    MyBI.ulFlags = Bif_ReturnOnlyFSDirs
    FList = SHBrowseForFolder(MyBI)
    SelFolder = SHGetPathFromIDList(FList, DirName)
    DirName = Left(DirName, InStr(1, DirName, Chr(0)) - 1)
    
    If DirName <> " " Then
        PathDGN = DirName
    Else
        PathDGN = ""
    End If
    
    UserForm1.TextBox_FromFolder.Text = PathDGN
    PopulateFileList
End Sub

Sub PopulateFileList()
    UserForm1.ListBox_CuttingFiles.Clear
    Dim myFolder As Folder
    Dim myFSO As New FileSystemObject
    Dim chkSubFolders As Boolean
    
    If UserForm1.TextBox_FromFolder.Text <> "" Then
        Set myFolder = myFSO.GetFolder(UserForm1.TextBox_FromFolder.Text)
        FilesInFolder myFolder, "dgn", chkSubFolders, UserForm1.ListBox_CuttingFiles
    End If
    UserForm1.lblFiles.Caption = "Design Files in Folder - " & UserForm1.ListBox_CuttingFiles.ListCount & " Files Found."
End Sub

Sub FilesInFolder(FolderIn As Folder, FileExtension As String, Includesubs As Boolean, ListToPopulate As ListBox)
    Dim myFile As File

    For Each myFile In FolderIn.Files
        Select Case UCase(FileExtension)
            Case UCase(Right(myFile.Name, 3))
                ListToPopulate.AddItem Right(myFile.Path, Len(myFile.Path) - InStrRev(myFile.Path, "\"))
        End Select
    Next
End Sub
Sub SelectTargetFolder(textBox As textBox)
    Dim MyBI As BrowseInfo
    Dim FList As Long
    Dim DirName As String
    Dim SelFolder As Long
    DirName = Space(255)
    
    MyBI.sTitle = "Выбрать папку для результатов нарезки:"
    MyBI.sDisplayName = Space(255)
    MyBI.ulFlags = Bif_ReturnOnlyFSDirs
    FList = SHBrowseForFolder(MyBI)
    SelFolder = SHGetPathFromIDList(FList, DirName)
    DirName = Left(DirName, InStr(1, DirName, Chr(0)) - 1)
    
    If DirName <> " " Then
        textBox.Text = DirName
    Else
        textBox.Text = ""
    End If
End Sub
Function FindFileInFolder(targetPath As String, fName As String) As Boolean
    Dim myFolder As Folder
    Dim myFile As File
    Dim myFSO As New FileSystemObject
    
    If targetPath <> "" Then
        Set myFolder = myFSO.GetFolder(UserForm1.TextBoxTargetPathFiles.Text)
        For Each myFile In myFolder.Files
            If UCase(Right(myFile.Name, 3)) = "DGN" Then
                If myFile.Path = fName Then
                    FindFileInFolder = True
                    Exit Function
                Else
                    FindFileInFolder = False
                End If
            End If
        Next
    End If
End Function
Sub ReadFilesPath()
    Dim i As Long
    ReDim CuttingFilesPath(0)
    For i = 1 To UserForm1.ListBox_CuttingFiles.ListCount
        If UserForm1.ListBox_CuttingFiles.Selected(i - 1) = True Then
            CuttingFilesPath(UBound(CuttingFilesPath)) = UserForm1.ListBox_CuttingFiles.List(i - 1)
            ReDim Preserve CuttingFilesPath(UBound(CuttingFilesPath) + 1)
        End If
    Next i
    ReDim Preserve CuttingFilesPath(UBound(CuttingFilesPath) - 1)
End Sub

Public Sub Copy_dgn()
    Dim PathDGN As String
    
    PathDGN = Left(dgntmpName, InStr(1, dgntmpName, ".dgn") - 1)
    Debug.Print PathDGN
    CopyDesignFile dgntmpName, PathDGN & "_copy.dgn", True
    
End Sub

Sub Main()
    UserForm1.Show vbModeless
End Sub

Attribute VB_Name = "UserForm1"
Attribute VB_Base = "0{C14245F1-4E0F-4016-AFBF-60D3C3E73274}{4FDAE215-A8FB-4F43-8146-95A0CF349903}"
Attribute VB_GlobalNameSpace = False
Attribute VB_Creatable = False
Attribute VB_PredeclaredId = True
Attribute VB_Exposed = False
Attribute VB_TemplateDerived = False
Attribute VB_Customizable = False
Option Explicit

Private Sub IniLevels()
    Dim myLevel As Level
        UserForm1.ComboBox_Levels.Clear
            For Each myLevel In ActiveDesignFile.Levels
                UserForm1.ComboBox_Levels.AddItem myLevel.Name
            Next
End Sub

Private Sub CommandButton_Analize_Click()
    AnalizeIntersect
    
End Sub

Private Sub CommandButton_copyDGN_Click()
    Copy_dgn
End Sub

Private Sub CommandButton_Select_tmp_Click()
    Module1.Select_temp
    Debug.Print dgntmpName
End Sub

Private Sub CommandButton_tarFolder_Click()
    Module1.SelectFolder
End Sub

Private Sub CommandButton1_Click()
    ReadFilesPath
    CopyFenceContents
End Sub

Private Sub CommandButtonSelectTargetPath_Click()
    Module1.SelectTargetFolder TextBoxTargetPathFiles
End Sub

Private Sub UserForm_Initialize()
    IniLevels
End Sub

Sub Copy_element(curElement() As Element, suff As String)
    Dim df As DesignFile
    Dim oMDL As ModelReference
    Dim i As Long
    
    Dim cc As New CopyContext
    Dim myFileName As String
    
    myFileName = TextBoxTargetPathFiles & "\" & TextBox_targetFileName.Text & suff & ".dgn"
    
    If Module1.FindFileInFolder(TextBoxTargetPathFiles, myFileName) Then
        Set df = OpenDesignFileForProgram(myFileName, False)
    Else
        CreateDesignFile "seed3d", myFileName, False
        Set df = OpenDesignFileForProgram(myFileName, False)
    End If
    Set oMDL = df.DefaultModelReference
    cc.LevelHandling = msdCopyContextLevelCopyAlways
    
    For i = 0 To UBound(curElement)
'        If curElement(i).Type = msdElementTypeSolid Then
'            oMDL.CopyElement curElement(i).AsSmartSolidElement.FacetSolidAsMesh(100, 100, 1, 5), cc
'        Else
            oMDL.CopyElement curElement(i), cc
'        End If
        ActiveModelReference.RemoveElement curElement(i)
        curElement(i).Redraw
    Next i
     
    df.Save
    Set cc = Nothing
    df.RewriteLevels
    df.Save
End Sub

 Sub CopyFenceContents()
    Dim fnc As Fence
    Dim ee As ElementEnumerator
    Dim saveClip As Boolean
    Dim saveOverlap As Boolean
    Dim saveVoid As Boolean
    Dim i As Long
    
    Dim myElement As Element
    Dim myEnum As ElementEnumerator
    Dim mFilter As New ElementScanCriteria
    Dim myView As View
    Dim myElems() As Element
    Dim myFences() As Element
    Dim j As Long
    
    Dim oFile As DesignFile
    Dim sFullFileName As String
    
    Dim df As DesignFile
    Dim f As Long
    Dim cutFilePath As String
    Dim oMDL As ModelReference
    Dim cc As New CopyContext
    Dim myFencesIN() As Element
    Dim refFilter As New ElementScanCriteria
    Dim solidElement As Element
    
    mFilter.ExcludeAllLevels
    mFilter.ExcludeAllTypes
    
    mFilter.IncludeLevel ActiveDesignFile.Levels(UserForm1.ComboBox_Levels.Text)
    mFilter.IncludeType msdElementTypeShape
    mFilter.IncludeType msdElementTypeComplexShape
    
    With ActiveSettings
        saveClip = .FenceClip
        .FenceClip = True
        saveOverlap = .FenceOverlap
        .FenceOverlap = False
        saveVoid = .FenceVoid
        .FenceVoid = False
    End With
    
    Set myEnum = ActiveModelReference.Scan(mFilter)
    myFences = myEnum.BuildArrayFromContents
    
    Set fnc = ActiveDesignFile.Fence
    fnc.Undefine
    
    For f = 0 To UBound(CuttingFilesPath)
        cutFilePath = PathDGN & "\" & CuttingFilesPath(f)
        Set df = OpenDesignFileForProgram(cutFilePath, False)
        Set oMDL = df.DefaultModelReference

        Set myEnum = oMDL.Scan(refFilter)
        myFencesIN = myEnum.BuildArrayFromContents
        cc.LevelHandling = msdCopyContextLevelCopyAlways
        For j = 0 To UBound(myFencesIN)
            Debug.Print myFencesIN(j).Type
            On Error Resume Next
'            If myFencesIN(j).Type = msdElementTypeCellHeader Then
'                Set solidElement = myFencesIN(j).AsSmartSolidElement.FacetSolidAsMesh(100, 100, 1, 5)
'                solidElement.Level = myFencesIN(j).Level
'                oMDL.AddElement solidElement
'                ActiveModelReference.CopyElement solidElement, cc
'            Else
                ActiveModelReference.CopyElement myFencesIN(j), cc
         '  End If
        Next j
        Set cc = Nothing
        df.Close
        ActiveDesignFile.RewriteLevels
        SolidToMesh
        For i = 0 To UBound(myFences)
            Set myView = ActiveDesignFile.Views(1)
            fnc.DefineFromElement myView, myFences(i)
            If Not fnc.IsDefined Then
                ShowError "The fence is not defined"
                Exit Sub
            End If
            ActiveDesignFile.Levels(UserForm1.ComboBox_Levels.Text).IsDisplayed = False
            Set ee = fnc.GetContents(True)
            myElems = ee.BuildArrayFromContents
            If UBound(myElems) > 0 Then
                
                Copy_element myElems, Format(CStr(i), UserForm1.TextBox_Razryd.Text)
            End If
            ActiveDesignFile.Levels(UserForm1.ComboBox_Levels.Text).IsDisplayed = True
        Next i
        ClearMergingElements
    Next f
    fnc.Undefine
    With ActiveSettings
        .FenceClip = saveClip
        .FenceOverlap = saveOverlap
        .FenceVoid = saveVoid
    End With
 End Sub
Private Sub ClearMergingElements()
    Dim myEnum As ElementEnumerator
    Dim mFilter As New ElementScanCriteria
    Dim mLevel As Level
    
    mFilter.ExcludeAllLevels
    
    For Each mLevel In ActiveDesignFile.Levels
        If mLevel.Name <> UserForm1.ComboBox_Levels.Text Then
            mFilter.IncludeLevel mLevel
        End If
    Next
    
    Set myEnum = ActiveModelReference.Scan(mFilter)
    
    While myEnum.MoveNext
        On Error Resume Next
        ActiveModelReference.RemoveElement myEnum.Current
        myEnum.Current.Redraw
    Wend
End Sub

Private Sub SolidToMesh()
    Dim mFilter As New ElementScanCriteria
    Dim mySolidEnum As ElementEnumerator
    Dim mMesh As Element
    
    mFilter.ExcludeAllTypes
    
    mFilter.IncludeType msdElementTypeCellHeader
    
    Set mySolidEnum = ActiveModelReference.Scan(mFilter)
    
    While mySolidEnum.MoveNext
        If mySolidEnum.Current.Type = msdElementTypeCellHeader Or mySolidEnum.Current.Type = msdElementTypeSolid Then
            ActiveModelReference.SelectElement mySolidEnum.Current
            
'            Set mMesh = mySolidEnum.Clone.AsSmartSolidElement.FacetSolidAsMesh(100, 100, 1, 5)
'            ActiveModelReference.AddElement mMesh
'            mMesh.Redraw
'            ActiveModelReference.RemoveElement mySolidEnum.Current
'            mySolidEnum.Current.Redraw
        End If
            CadInputQueue.SendCommand "FACET CREATE"
            CadInputQueue.SendDataPoint Point3dFromXYZ(0, 0, 0), 1
            CommandState.StartDefaultCommand
    Wend
    
    
End Sub
Sub AnalizeIntersect()
    Dim myEnum As ElementEnumerator
    Dim myEnumMesh As ElementEnumerator
    Dim mFilter As New ElementScanCriteria
    Dim mFilterMesh As New ElementScanCriteria
    Dim myElems() As Element
    Dim myElemsMesh() As Element
    Dim InterPoint() As Point3d
    Dim i As Long
    Dim j As Long
    
    mFilter.ExcludeAllLevels
    mFilter.ExcludeAllTypes
    mFilterMesh.ExcludeAllTypes
    mFilterMesh.IncludeType msdElementTypeMeshHeader
    
    mFilter.IncludeLevel ActiveDesignFile.Levels(UserForm1.ComboBox_Levels.Text)
    mFilter.IncludeType msdElementTypeShape
    mFilter.IncludeType msdElementTypeComplexShape
    
    Set myEnum = ActiveModelReference.Scan(mFilter)
    Set myEnumMesh = ActiveModelReference.Scan(mFilterMesh)
    myElems = myEnum.BuildArrayFromContents
    myElemsMesh = myEnumMesh.BuildArrayFromContents
    
    For i = 0 To UBound(myElems)
        For j = 0 To UBound(myElemsMesh)
            InterPoint = myElems(i).AsIntersectableElement.GetIntersectionPoints(myElemsMesh(j), Matrix3dIdentity)
                If UBound(InterPoint) <> -1 Then
                    myElems(i).Color = 3
                    myElems(i).Redraw
                    myElems(i).Rewrite
                End If
        Next j
    Next i
End Sub
