Attribute VB_Name = "Module1"
Public PTstart As Point3d
Public PTend As Point3d
Public Reset As Boolean
Sub GetXYZ()
    Dim myCIQ As CadInputQueue
    Dim myCIM As CadInputMessage
    Set myCIQ = CadInputQueue
    Reset = False
    ShowCommand "Нанесение текста"
    ShowPrompt "Укажите начальную точку"
    Set myCIM = myCIQ.GetInput(msdCadInputTypeDataPoint, msdCadInputTypeReset)
        Select Case myCIM.InputType
            Case msdCadInputTypeReset
                Exit Sub
            Case msdCadInputTypeDataPoint
                PTstart = myCIM.Point
        End Select
    CadInputQueue.SendCommand "PLACE LINE"
    CadInputQueue.SendDataPoint PTstart
    ShowCommand "Нанесение текста"
    ShowPrompt "Укажите конечную точку"
    Set myCIM = myCIQ.GetInput
        Select Case myCIM.InputType
            Case msdCadInputTypeReset
                Reset = True
                Exit Sub
            Case msdCadInputTypeDataPoint
                PTend = myCIM.Point
        End Select
End Sub
Function AngleTxt(pSt As Point3d, pEnd As Point3d) As Double
Dim dAng As Double
Dim Angel As Double
Dim ang As Double
Dim dx As Double
Dim dy As Double
dx = pEnd.X - pSt.X
dy = pEnd.Y - pSt.Y
If dy <> 0 Then
    ang = Atn(dx / dy)
    If dx >= 0 And dy > 0 Then
        dAng = ang
    ElseIf dx >= 0 And dy < 0 Then
        dAng = ang + Pi
    ElseIf dx < 0 And dy < 0 Then
        dAng = ang + Pi
    ElseIf dx < 0 And dy > 0 Then
        dAng = ang + 2 * Pi
    End If
ElseIf dy = 0 Then

    If dx > 0 Then
        dAng = Pi / 2
    ElseIf dx < 0 Then
        dAng = 3 * Pi / 4
    End If
End If
Angle = Pi / 2 - dAng
AngleTxt = Angle
End Function

Sub Main()
    Myform.Show vbModeless
    ShowCommand "Нанесение текста"
    ShowPrompt "Наберите текст"
End Sub

Attribute VB_Name = "Myform"
Attribute VB_Base = "0{ECB5DDCA-0636-4277-A330-18032D2797E6}{334DCD3A-BE4C-4480-93EA-B695C7FB06CA}"
Attribute VB_GlobalNameSpace = False
Attribute VB_Creatable = False
Attribute VB_PredeclaredId = True
Attribute VB_Exposed = False
Attribute VB_TemplateDerived = False
Attribute VB_Customizable = False
Function Distance3dpointToLine(stPt As Point3d, enPt As Point3d, tarPt As Point3d) As Double
Dim a As Double
Dim b As Double
Dim c As Double
Dim p As Double
Dim s As Double
Dim dist As Double
Dim L As Double
Dim D As Double
    a = Point3dDistance(stPt, tarPt)
    b = Point3dDistance(stPt, enPt)
    c = Point3dDistance(enPt, tarPt)
    p = (a + b + c) / 2
    s = Sqr(p * (p - a) + (p - b) * (p - c))
    L = (a ^ 2 + b ^ 2 - c ^ 2) / 2 * a * b
    D = (b ^ 2 + c ^ 2 - a ^ 2) / 2 * b * c
    If L >= 0 And D >= 0 Then
        If b = 0 Then
            dist = a
        Else: dist = 2 * s / b
        End If
    ElseIf L < 0 Or D < 0 Then
        dist = -1
    End If
Distance3dpointToLine = dist
End Function
Sub DrawText()
Dim text As String
    Dim fEng As Font
    Dim RotationMatrix As Matrix3d
    Dim TextElem As TextElement
       If opTmp.Value = True Then
          If txtbNumber.text = "" Then
                text = CMBroad.text
          Else
            text = CMBroad.text & " N " & txtbNumber.text
          End If
        ElseIf opTxt.Value = True Then
            text = txtbText.text
        ElseIf opETL.Value = True Then
            If txtKV.text = "" Then
                text = cmbEtl.text
            Else
            text = cmbEtl.text & " " & txtKV.text & "kV"
            End If
        End If
            If cbStyle.Value = True Then
                ActiveSettings.TextStyle.Height = 5
                ActiveSettings.TextStyle.Width = 5
                ActiveSettings.TextStyle.InterCharacterSpacing = 0
                'ActiveSettings.TextStyle = ActiveDesignFile.TextStyles("STANDARD")
                ActiveSettings.TextStyle.Font = ActiveDesignFile.Fonts("ENGINEERING")
                ActiveSettings.TextStyle.Justification = msdTextJustificationLeftBottom
            End If
        RotationMatrix = Matrix3dFromAxisAndRotationAngle(2, AngleTxt(PTstart, PTend))
        Set TextElem = CreateTextElement1(Nothing, text, PTstart, RotationMatrix)
            If cbStyle.Value = True Then
                TextElem.Level = ActiveDesignFile.Levels("Text")
            End If
    ActiveModelReference.AddElement TextElem
    TextElem.Redraw (msdDrawingModeHilite)
    CadInputQueue.SendReset
    txtbNumber.text = ""
    txtKV.text = ""
End Sub
Sub SerchRoad()
    Dim myEnum As ElementEnumerator
    Dim myEnumCS As ElementEnumerator
    Dim myFilter As New ElementScanCriteria
    Dim myShape As ShapeElement
    Dim myLine As LineElement
    Dim tarShape As ShapeElement
    Dim tarCShape As ComplexShapeElement
    Dim curVert As Point3d
    Dim minDist As Double
    Dim dist As Double
    Dim myCShape As ComplexShapeElement
    Dim idCount As Double
    Dim vertxCount As Double
    Dim nameLv As String
    Dim i As Long
    Dim tarElem As Element
    
    myFilter.ExcludeAllTypes
    myFilter.ExcludeAllLevels
    myFilter.IncludeLevel ActiveDesignFile.Levels("Other road")
    myFilter.IncludeLevel ActiveDesignFile.Levels("Department road RD")
    myFilter.IncludeLevel ActiveDesignFile.Levels("National road RN")
    myFilter.IncludeLevel ActiveDesignFile.Levels("Highway A")
    myFilter.IncludeLevel ActiveDesignFile.Levels("Commune road VC")
    myFilter.IncludeType msdElementTypeShape
    myFilter.IncludeType msdElementTypeComplexShape
    Set myEnum = ActiveModelReference.Scan(myFilter)
    minDist = 10000
        While myEnum.MoveNext
        
        
        
            Select Case myEnum.Current.Type
                Case msdElementTypeShape
                    Set myShape = myEnum.Current
                    Debug.Print myShape.FilePosition
                    
                    For i = 1 To (myShape.VerticesCount - 1)
                        dist = Distance3dpointToLine(myShape.Vertex(i), myShape.Vertex(i + 1), PTstart)
                        If dist > 0 And dist < minDist Then
                            minDist = dist
                            Set tarElem = myShape
                        End If
                    Next i
                Case msdElementTypeComplexShape
                    Set myCShape = myEnum.Current
                    Set myEnumCS = myCShape.GetSubElements
                        While myEnumCS.MoveNext
                            Set myLine = myEnumCS.Current
                            For i = 1 To (myLine.VerticesCount - 1)
                                dist = Distance3dpointToLine(myLine.Vertex(i), myLine.Vertex(i + 1), PTstart)
                                If dist > 0 And dist < minDist Then
                                    minDist = dist
                                    Set tarElem = myCShape
                                End If
                            Next i
                        Wend
            End Select
        Wend
   Select Case CMBroad.text
        Case "R.D."
            nameLv = "Department road RD"
        Case "R.N."
            nameLv = "National road RN"
        Case "A."
            nameLv = "Highway A"
        Case "V.C."
            nameLv = "Commune road VC"
        Case "C.O."
            nameLv = "Commune road VC"
        Case "C.R."
            nameLv = "Commune road VC"
        Case "C.E."
            nameLv = "Commune road VC"
        Case "R.F."
            nameLv = "Commune road VC"
        Case "C.V."
            nameLv = "Commune road VC"
        Case "C.V.O."
            nameLv = "Commune road VC"
        Case "RIVIERE"
            Exit Sub
        Case "RUISSEAU"
            Exit Sub
        Case "S.N.C.F."
            Exit Sub
    End Select
    'ActiveModelReference.RemoveElement tarElem
    tarElem.Level = ActiveModelReference.Levels(nameLv)
    'ActiveModelReference.AddElement tarElem
    tarElem.Rewrite
    tarElem.Redraw
        Debug.Print idCount
        Debug.Print vertxCount
End Sub

Private Sub cbLevel_Click()

End Sub

Private Sub cbtWrite_Click()
    CadInputQueue.SendReset
    CadInputQueue.SendReset
    GetXYZ
        If Reset = True Then
            Exit Sub
        End If
    DrawText
    If cbLevel.Value = True Then
        SerchRoad
    End If
End Sub
Private Sub cmbEtl_Change()
    opETL.Value = True
End Sub
Private Sub CMBroad_Change()
    opTmp.Value = True
End Sub
Private Sub opTmp_Change()
    If opTmp.Value = False Then
    cbLevel.Value = False
        cbLevel.Enabled = False
    ElseIf opTmp.Value = True Then
       cbLevel.Enabled = True
       cbLevel.Value = True
    End If
End Sub
Private Sub txtbText_Enter()
    opTxt.Value = True
End Sub
Private Sub UserForm_Initialize()
    CMBroad.AddItem "R.N."
    CMBroad.AddItem "R.D."
    CMBroad.AddItem "V.C."
    CMBroad.AddItem "C.O."
    CMBroad.AddItem "C.E."
    CMBroad.AddItem "C.R."
    CMBroad.AddItem "R.F."
    CMBroad.AddItem "C.V."
    CMBroad.AddItem "C.V.O."
    CMBroad.AddItem "A."
    CMBroad.AddItem "S.N.C.F."
    CMBroad.AddItem "RIVIERE"
    CMBroad.AddItem "RUISSEAU"
    cmbEtl.AddItem "HTB"
    cmbEtl.AddItem "HTA"
    cmbEtl.AddItem "BT"
    cmbEtl.AddItem "HT"
    cmbEtl.AddItem "MT"
    cmbEtl.AddItem "DGT"
    cmbEtl.AddItem "PT"
    cmbEtl.AddItem "PTT"
End Sub
