Attribute VB_Name = "Module1"
Sub Main()
    UserForm1.Show vbModeless
End Sub

Attribute VB_Name = "UserForm1"
Attribute VB_Base = "0{1D1153B2-589C-4C77-9FA2-92C96BE7DEFF}{1D7324B2-0DED-489B-AE3D-932E92BE3C0D}"
Attribute VB_GlobalNameSpace = False
Attribute VB_Creatable = False
Attribute VB_PredeclaredId = True
Attribute VB_Exposed = False
Attribute VB_TemplateDerived = False
Attribute VB_Customizable = False

Private Sub IniLevels(mListBox As ComboBox)
    Dim MyLevel As Level
        mListBox.Clear
        For Each MyLevel In ActiveDesignFile.Levels
                mListBox.AddItem MyLevel.Name
        Next
End Sub
Private Sub CommandButtonConverte_Click()
    CreateCentroid
End Sub

Private Sub UserForm_Initialize()
    IniLevels ComboBoxLevels
End Sub
Private Sub CreateCentroid()
    Dim mEnum As ElementEnumerator
    Dim mFilter As New ElementScanCriteria
    Dim mCentroid As LineElement
    Dim mPoint As Point3d
    
    If ActiveModelReference.AnyElementsSelected Then
        Set mEnum = ActiveModelReference.GetSelectedElements
    Else
        MsgBox "No fence or selection set defined.", vbOKOnly Or vbExclamation, "Error"
        Exit Sub
    End If
    
    While mEnum.MoveNext
        If mEnum.Current.Type = msdElementTypeShape Then ComputeCentroidOfPolygon mEnum.Current.AsShapeElement
        
    Wend
End Sub

Private Sub ComputeCentroidOfPolygon(ByVal mShape As ShapeElement)
    Dim mVert() As Point3d
    Dim mCentroids() As Point3d
    Dim mAreas() As Double
    Dim Area As Double
    Dim CS As Point3d
    Dim i As Long
    Dim k As Long
    
    mShape.Transform Transform3dFromMatrix3dPoint3d(Matrix3dFromScaleFactors(1, 1, 0), Point3dFromXYZ(0, 0, 0))
    mVert = mShape.GetVertices
    k = UBound(mVert) - 1
    ReDim mCentroids(k)
    ReDim mAreas(k)
    
    For i = 0 To k
        mCentroids(i) = ComputeCentroidOfTriangle(mVert(i), mVert(i + 1))
        mAreas(i) = ComputeAreaOfTriangle(mVert(i), mVert(i + 1))
        CS = Point3dAdd(CS, Point3dScale(mCentroids(i), mAreas(i)))
        Area = Area + mAreas(i)
    Next i
        CS = Point3dScale(CS, 1 / Area)
       ' DrawPoint3d CS, 1
        DrawPoint3d GetMidPoint1(CS, mShape), 3
        
End Sub

Private Function GetMidPoint1(mCentroid As Point3d, mShape As ShapeElement) As Point3d
    Dim mLine As LineElement
    Dim iPoint() As Point3d
    Dim mVector As Vector3d
    Dim pPoint As Point3d 'Проекция на элемент
    Dim mPoint As Point3d 'Средняя точка отрезка
    Dim bInside As Boolean
    
    pPoint = mShape.ProjectPointOnPerpendicular2(mCentroid, Matrix3dIdentity)
   ' DrawPoint3d pPoint, 3
    If Point3dInPolygonXY(mCentroid, mShape.GetVertices) > 0 Then
        mVector = Vector3dSubtractPoint3dPoint3d(mCentroid, pPoint)
        bInside = True
    Else
        mVector = Vector3dSubtractPoint3dPoint3d(pPoint, mCentroid)
    End If
    
    mVector = Vector3dScale(mVector, 1000)
    Set mLine = CreateLineElement2(Nothing, pPoint, Point3dAdd(pPoint, Point3dFromVector3d(mVector)))
    iPoint = mLine.GetIntersectionPoints(mShape, Matrix3dIdentity)
    If UBound(iPoint) > 0 Then
        mPoint = Point3dInterpolate(iPoint(0), 0.5, iPoint(1))
            If bInside = True Then
                If Point3dDistance(iPoint(0), iPoint(1)) * 0.3 <= Point3dDistance(mCentroid, pPoint) Then
                    mPoint = mCentroid
                End If
            End If
    End If
    GetMidPoint1 = mPoint
End Function

Private Sub DrawPoint3d(mPoint As Point3d, color As Long)
    Dim lCentroid As LineElement
    
    Set lCentroid = CreateLineElement2(Nothing, mPoint, mPoint)
    lCentroid.color = color
    lCentroid.LineWeight = 1
    lCentroid.Level = ActiveDesignFile.Levels.Find(ComboBoxLevels.Text)
    ActiveModelReference.AddElement lCentroid
    
    lCentroid.Redraw
End Sub
Private Function ComputeCentroidOfTriangle(p1 As Point3d, p2 As Point3d) As Point3d
    Dim p0 As Point3d
    
    ComputeCentroidOfTriangle = Point3dScale(Point3dAdd2Scaled(p0, p1, 1, p2, 1), 1 / 3)
End Function

Private Function ComputeAreaOfTriangle(p1 As Point3d, p2 As Point3d) As Double
    Dim p0 As Point3d
    
    ComputeAreaOfTriangle = CrossProduct(p1, p2) * 0.5
End Function

Private Function CrossProduct(p1 As Point3d, p2 As Point3d) As Double

    CrossProduct = p1.X * p2.Y - p2.X * p1.Y
End Function
