Attribute VB_Name = "Module1"
Option Explicit

Sub Main()
    UserForm1.Show vbModeless
End Sub

Attribute VB_Name = "UserForm1"
Attribute VB_Base = "0{1451A89C-680D-4A91-ACC9-9D6C2B363D2F}{32D6AF20-2DA2-4F2D-AE0B-E594D5B6F1CA}"
Attribute VB_GlobalNameSpace = False
Attribute VB_Creatable = False
Attribute VB_PredeclaredId = True
Attribute VB_Exposed = False
Attribute VB_TemplateDerived = False
Attribute VB_Customizable = False
Option Explicit

Sub InizialisationCells()
    Dim MyEnum As ElementEnumerator
    Dim myFilter As New ElementScanCriteria
    Dim MyCell As SharedCellElement
    Dim i As Integer
    Dim bool As Boolean

    UserForm1.ComboBox_cell.Clear
    myFilter.ExcludeAllTypes
    'myFilter.IncludeType msdElementTypeCellHeader
    myFilter.IncludeType msdElementTypeSharedCell
    
    Set MyEnum = ActiveModelReference.Scan(myFilter)
    
    While MyEnum.MoveNext
        Set MyCell = MyEnum.Current
            Do
                For i = 0 To UserForm1.ComboBox_cell.ListCount - 1
                    If UserForm1.ComboBox_cell.List(i, 0) = MyCell.Name Then
                        Exit Do
                    End If
                Next i
                UserForm1.ComboBox_cell.AddItem MyCell.Name
        Loop While bool = True
    Wend
End Sub

Private Sub CommandButton_find_Click()
    FindText
End Sub

Private Sub UserForm_Initialize()
    InizialisationCells
End Sub

Sub FindText()
    Dim MyEnum As ElementEnumerator
    Dim myFilter As New ElementScanCriteria
    Dim MyCell As SharedCellElement
    
    Dim MyEnumT As ElementEnumerator
    Dim myFilterT As New ElementScanCriteria
    Dim MyText As TextElement
    Dim myTxtArr() As Element
    Dim i As Double
    
    Dim minDist As Double
    Dim curDist As Double
    Dim Roun As Double
    Dim rng As Range3d
    Dim fText As TextElement
    Dim DistL As LineElement
        
    minDist = CDbl(TextBox_minDist.Text)
    
    myFilter.ExcludeAllTypes
    myFilter.IncludeType msdElementTypeSharedCell
    
    myFilterT.ExcludeAllTypes
    myFilterT.IncludeType msdElementTypeText
    
    Set MyEnum = ActiveModelReference.Scan(myFilter)
    Set MyEnumT = ActiveModelReference.Scan(myFilterT)
    myTxtArr = MyEnumT.BuildArrayFromContents
    
    While MyEnum.MoveNext
        Set MyCell = MyEnum.Current
            For i = 0 To UBound(myTxtArr)
                rng = myTxtArr(i).AsTextElement.Boundary
                curDist = DistanceToRange(myTxtArr(i).AsTextElement, MyCell.Origin)
              '  curDist = Point3dDistanceXY(MyCell.Origin, myTxtArr(i).AsTextElement.Origin)
                
                
              '  rng.Low = myTxtArr(i).AsTextElement.Origin
'                If Range3dContainsPoint3d(rng, Point3dFromXY(MyCell.Origin.X, MyCell.Origin.Y)) Then
'                    Set fText = myTxtArr(i).AsTextElement
'                    Exit For
'                End If
                    If curDist < minDist Then
                        Set fText = myTxtArr(i).AsTextElement
                        minDist = curDist
                    End If
'                DrawPoint rng.Low, 1
'                DrawPoint rng.High, 3
            Next i
        On Error Resume Next
        
        If Not fText Is Nothing Then
        Set DistL = CreateLineElement2(Nothing, MyCell.Origin, fText.Origin)
        ActiveModelReference.AddElement DistL
            Roun = Round(MyCell.Origin.Z, 2)
            If Abs((Roun - CDbl(fText.Text))) > CDbl(TextBox_tolerance.Text) Then
                DistL.Color = 3
                DistL.LineWeight = 3
            End If
        DistL.Redraw
        DistL.Rewrite
        minDist = CLng(TextBox_minDist.Text)
        Set fText = Nothing
        End If
        
    Wend
        
End Sub
Function RoundMath(Tochn As Double, iR As Integer) As Double
    Dim Rounded As Double, HTochn As Double, TTochn As Double
    Dim HTochnCroped As Long, TTochnCroped As Long, IDelta As Integer
    HTochn = Tochn * 10 ^ iR
    TTochn = HTochn * 10
    HTochnCroped = Fix(HTochn)
    TTochnCroped = HTochnCroped * 10
    IDelta = TTochn - TTochnCroped
 
    If (IDelta >= 5) Then
        Rounded = ((HTochnCroped + 1) / (10 ^ iR))
    Else
        Rounded = (HTochnCroped / (10 ^ iR))
    End If
 
    RoundMath = Rounded
End Function

Sub DrawPoint(mPoint As Point3d, col As Integer)
    Dim myLine As LineElement
    
    Set myLine = CreateLineElement2(Nothing, mPoint, mPoint)
    ActiveModelReference.AddElement myLine
    myLine.LineWeight = 3
    myLine.Color = col
    myLine.Rewrite
    myLine.Redraw
    
End Sub

Function DistanceToRange(mTxt As TextElement, mPoint As Point3d) As Double
    Dim p(0 To 3) As Point3d
    Dim mTxtRot As Double
    Dim rot As Double
    
    Dim sBoundary As Range3d
    
    Dim minDist As Double
    Dim dist As Double
    
    Dim i As Integer
    
    
    mTxtRot = GetAngleTxt(mTxt)
    If mTxtRot <> 0 Then
        rot = 2 * Pi - mTxtRot
        mTxt.RotateAboutZ mTxt.Origin, rot
        sBoundary = mTxt.Boundary
'        mTxt.Rewrite
'        mTxt.Redraw
    End If
    
    p(0) = mTxt.Origin
    
    p(1).X = sBoundary.Low.X
    p(1).Y = sBoundary.High.Y
    p(1) = Point3dAddAngleDistance(p(0), mTxtRot, Point3dDistanceXY(p(0), p(1)), 0)
    
    p(2) = Point3dAddAngleDistance(p(0), mTxtRot, Point3dDistanceXY(p(0), sBoundary.High), 0)
    
    p(3).X = sBoundary.High.X
    p(3).Y = sBoundary.Low.Y
    
    p(3) = Point3dAddAngleDistance(p(0), mTxtRot, Point3dDistanceXY(p(0), p(3)), 0)
    
    DrawPoint p(0), 1
    
    DrawPoint p(2), 3
    
    mPoint.Z = 0
    
    minDist = Dist_Segment_to_Point(p(0), p(1), mPoint)
    
    For i = 1 To 2
        dist = Dist_Segment_to_Point(p(i), p(i + 1), mPoint)
        If dist < minDist Then
            minDist = dist
        End If
    dist = Dist_Segment_to_Point(p(3), p(0), mPoint)
        If dist < minDist Then
            minDist = dist
        End If
    DistanceToRange = minDist
    Next i

End Function

Function GetAngleTxt(mTxt As TextElement) As Double
Dim rotationX As Double
Dim rotationY As Double
Dim rotationZ As Double
Dim scaleFactor As Double

If (Matrix3dIsXRotationYRotationZRotationScale(mTxt.Rotation, rotationX, rotationY, rotationZ, scaleFactor)) Then
        GetAngleTxt = rotationZ
End If

End Function
Private Function Dist_Segment_to_Point(StartPoint As Point3d, EndPoint As Point3d, iPoint As Point3d) As Double
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    
    vPoint = Vector3dSubtractPoint3dPoint3d(iPoint, StartPoint)
    vLine = Vector3dSubtractPoint3dPoint3d(EndPoint, StartPoint)
    
    c1 = Vector3dDotProduct(vPoint, vLine)
    c2 = Vector3dDotProduct(vLine, vLine)
        If c1 <= 0 Then
            Dist_Segment_to_Point = Point3dDistance(StartPoint, iPoint)
        ElseIf c2 <= c1 Then
            Dist_Segment_to_Point = Point3dDistance(EndPoint, iPoint)
        Else
            k = c1 / c2
            vProject = Vector3dScale(vLine, k)
            pProject = Vector3dAdd(Vector3dFromPoint3d(StartPoint), vProject)
            Dist_Segment_to_Point = Point3dDistance(Point3dFromVector3d(pProject), iPoint)
        End If
End Function
