Attribute VB_Name = "ComplexShapeToShape"
Option Explicit
Function ComplexShapeToShape(CShape As ComplexShapeElement) As ShapeElement
    Dim MyEnum As ElementEnumerator
    Dim MyShape As ShapeElement
    Dim Verteces() As Point3d
    Dim i As Integer
    ReDim Verteces(0)
        Set MyEnum = CShape.GetSubElements
            While MyEnum.MoveNext
                For i = 0 To UBound(MyEnum.Current.AsVertexList.GetVertices)
                    Verteces(UBound(Verteces)) = MyEnum.Current.AsLineElement.Vertex(i + 1)
                    ReDim Preserve Verteces(UBound(Verteces) + 1)
                Next i
                ReDim Preserve Verteces(UBound(Verteces) - 1)
            Wend
        Set MyShape = CreateShapeElement1(Nothing, Verteces, msdFillModeNotFilled)
        Set ComplexShapeToShape = MyShape
End Function

Attribute VB_Name = "CreateBuffer"
Option Explicit

Function Perpendicular(PP1 As Point3d, PP2 As Point3d, Of As Double) As Point3d()
    Dim PP(0 To 3) As Point3d ' Искомые точки перпендикуляров
                                ' 0 - 1 - перпендикуляры на начале отрезка Лево - Право, соответственно
                                ' 2 - 3 - перпендикуляры на конце отрезка Лево - Право, соответственно
    Dim Ax As Double
    Dim Ay As Double
    Dim vLine As Vector3d   ' Отрезок осевой линии
    Dim vRoad As Vector3d   ' Точка сдвига относительно осевой линии
    Ax = PP2.X - PP1.X
    Ay = PP2.Y - PP1.Y
    
    
    vLine = Vector3dFromXY(Ax, Ay)
    vRoad = Vector3dUnitPerpendicularXY(vLine)
    vRoad = Vector3dScale(vRoad, Of)
    PP(0).X = Vector3dGetComponent(vRoad, 0) + PP1.X
    PP(0).Y = Vector3dGetComponent(vRoad, 1) + PP1.Y
    PP(2).X = Vector3dGetComponent(vRoad, 0) + PP2.X
    PP(2).Y = Vector3dGetComponent(vRoad, 1) + PP2.Y
    vRoad = Vector3dScale(vRoad, -1)
    PP(1).X = Vector3dGetComponent(vRoad, 0) + PP1.X
    PP(1).Y = Vector3dGetComponent(vRoad, 1) + PP1.Y
    PP(3).X = Vector3dGetComponent(vRoad, 0) + PP2.X
    PP(3).Y = Vector3dGetComponent(vRoad, 1) + PP2.Y
    Perpendicular = PP
    

End Function

Function IntersectionLines(PP1 As Point3d, PP2 As Point3d, PP3 As Point3d, PP4 As Point3d) As Point3d
    Dim k1 As Double
    Dim k2 As Double
    Dim b1 As Double
    Dim b2 As Double
    
    If PP1.X = PP2.X And PP3.X = PP4.X And PP2.X = PP3.X Then
                IntersectionLines.X = PP2.X
                IntersectionLines.Y = PP2.Y
        ElseIf PP1.Y = PP2.Y And PP3.Y = PP4.Y And PP2.Y = PP3.Y Then
                    IntersectionLines.X = PP2.X
                    IntersectionLines.Y = PP2.Y
        ElseIf PP3.X = PP4.X Then
            k1 = (PP2.Y - PP1.Y) / (PP2.X - PP1.X)
            b1 = (PP1.Y * PP2.X - PP2.Y * PP1.X) / (PP2.X - PP1.X)
            IntersectionLines.X = PP3.X
            IntersectionLines.Y = k1 * PP3.X + b1
        ElseIf PP1.X = PP2.X Then
            k2 = (PP4.Y - PP3.Y) / (PP4.X - PP3.X)
            b2 = (PP3.Y * PP4.X - PP4.Y * PP3.X) / (PP4.X - PP3.X)
            IntersectionLines.X = PP1.X
            IntersectionLines.Y = k2 * PP1.X + b2
        Else
            k1 = (PP2.Y - PP1.Y) / (PP2.X - PP1.X)
            b1 = (PP1.Y * PP2.X - PP2.Y * PP1.X) / (PP2.X - PP1.X)
            k2 = (PP4.Y - PP3.Y) / (PP4.X - PP3.X)
            b2 = (PP3.Y * PP4.X - PP4.Y * PP3.X) / (PP4.X - PP3.X)
            IntersectionLines.X = (b2 - b1) / (k1 - k2)
            IntersectionLines.Y = (k1 * (b2 - b1) / (k1 - k2)) + b1
    End If
End Function


Function BufferFromShape(iShape As ShapeElement, offset As Double) As ShapeElement
    Dim lShape() As Point3d
    Dim rShape() As Point3d
    Dim iniShape() As Point3d
    Dim tarShape() As Point3d
    Dim vCount As Long ' Количество вертексов иходного шейпа
    Dim i As Integer
    Dim PP(0 To 3) As Point3d
    Dim shape1 As ShapeElement
    Dim shape2 As ShapeElement
    ReDim tarShape(0)
    Dim j As Integer
    Dim t As Integer
    iniShape = iShape.GetVertices
    
    Do While j < UBound(iniShape)
        tarShape(t) = iniShape(j)
        j = j + 1
        t = t + 1
        If Point3dEqual(iniShape(j), iniShape(j - 1)) = True Then
            j = j + 1
        End If
        ReDim Preserve tarShape(UBound(tarShape) + 1)
    Loop
        tarShape(UBound(tarShape)) = tarShape(0)
    
    ReDim Preserve rShape(UBound(tarShape) - 1)
    ReDim Preserve lShape(UBound(tarShape) - 1)
    vCount = UBound(tarShape)
    
    For i = 0 To (vCount - 1)
        If i = 0 Then
            PP(0) = Perpendicular(tarShape(vCount - 1), tarShape(i), offset)(0)
            PP(1) = Perpendicular(tarShape(vCount - 1), tarShape(i), offset)(2)
            PP(2) = Perpendicular(tarShape(i), tarShape(i + 1), offset)(0)
            PP(3) = Perpendicular(tarShape(i), tarShape(i + 1), offset)(2)
            lShape(i) = IntersectionLines(PP(0), PP(1), PP(2), PP(3))
            PP(0) = Perpendicular(tarShape(vCount - 1), tarShape(i), offset)(1)
            PP(1) = Perpendicular(tarShape(vCount - 1), tarShape(i), offset)(3)
            PP(2) = Perpendicular(tarShape(i), tarShape(i + 1), offset)(1)
            PP(3) = Perpendicular(tarShape(i), tarShape(i + 1), offset)(3)
            rShape(i) = IntersectionLines(PP(0), PP(1), PP(2), PP(3))
        Else
            PP(0) = Perpendicular(tarShape(i - 1), tarShape(i), offset)(0)
            PP(1) = Perpendicular(tarShape(i - 1), tarShape(i), offset)(2)
            PP(2) = Perpendicular(tarShape(i), tarShape(i + 1), offset)(0)
            PP(3) = Perpendicular(tarShape(i), tarShape(i + 1), offset)(2)
            lShape(i) = IntersectionLines(PP(0), PP(1), PP(2), PP(3))
            PP(0) = Perpendicular(tarShape(i - 1), tarShape(i), offset)(1)
            PP(1) = Perpendicular(tarShape(i - 1), tarShape(i), offset)(3)
            PP(2) = Perpendicular(tarShape(i), tarShape(i + 1), offset)(1)
            PP(3) = Perpendicular(tarShape(i), tarShape(i + 1), offset)(3)
            rShape(i) = IntersectionLines(PP(0), PP(1), PP(2), PP(3))
        End If
    Next i
    
    Set shape1 = CreateShapeElement1(Nothing, lShape)
    Set shape2 = CreateShapeElement1(Nothing, rShape)
  ' ActiveModelReference.AddElement shape1
  ' shape1.Redraw
    
    If shape1.Area > shape2.Area Then
        Set BufferFromShape = shape1
    ElseIf shape1.Area < shape2.Area Then
        Set BufferFromShape = shape2
    End If
    
    Erase lShape
    Erase rShape
    Erase iniShape
    Erase tarShape
End Function

Attribute VB_Name = "CreateRegion"
Option Explicit

Sub GetCorridorsFromReference(Candidates() As Element)
    Dim myAttach As Attachment
    Dim myFilter As New ElementScanCriteria
    Dim myElemFilter As New ElementScanCriteria
    Dim myEnumElement As ElementEnumerator
    Dim Corridors() As ShapeElement
    Dim MyElements() As Element 'Элементы для расширения
    Dim MyEnum As ElementEnumerator
    Dim i As Integer
    Dim j As Integer
    
    ReDim Corridors(0)
    ReDim MyElements(0)
    
    Set myAttach = ActiveDesignFile.DefaultModelReference.Attachments(FormSKPM.cmbReference.ListIndex + 1)
    
    myFilter.ExcludeAllTypes
    myFilter.ExcludeAllLevels
    
    myFilter.IncludeType msdElementTypeShape
    myFilter.IncludeLevel myAttach.Levels.FindByNumber(CLng(FormSKPM.tbLevelCorridor.Text))
    
    
    myElemFilter.ExcludeAllLevels
    myElemFilter.ExcludeAllTypes
    
    If FormSKPM.cbElementOffset.Value = True Then
        myElemFilter.IncludeType msdElementTypeShape
        myElemFilter.IncludeType msdElementTypeComplexShape
        
        For j = 1 To ufLevelsForOffset.lbLevels.ListCount
            If ufLevelsForOffset.lbLevels.Selected(j - 1) Then
                myElemFilter.IncludeLevel ActiveModelReference.Levels.Find(ufLevelsForOffset.lbLevels.List(j - 1))
            End If
        Next j
        
'        For j = 0 To UBound(Split(FormSKPM.tbElementOffsetLvl.Text, ","))
'            myElemFilter.IncludeLevel ActiveModelReference.Levels.FindByNumber(Split(FormSKPM.tbElementOffsetLvl.Text, ",")(j))
'        Next j
        
        
        Set myEnumElement = ActiveModelReference.Scan(myElemFilter) ' Сканирование дорог
        While myEnumElement.MoveNext
                Set MyElements(UBound(MyElements)) = myEnumElement.Current
                    ReDim Preserve MyElements(UBound(MyElements) + 1)
        Wend
    
        j = 0
            If UBound(MyElements) > 0 Then
                ReDim Preserve MyElements(UBound(MyElements) - 1)
                i = (UBound(Candidates) + 1)
                For i = i To (i + UBound(MyElements))
                    ReDim Preserve Candidates(UBound(Candidates) + 1)
                    If MyElements(j).Type = msdElementTypeComplexShape Then
                        Set MyElements(j) = ComplexShapeToShape.ComplexShapeToShape(MyElements(j)) ' Преобразование complexShape в Shape
                    End If
                    On Error GoTo errnocreateBuffer ' Если не создался буфер, то пропускается элемент
                        Set Candidates(i) = CreateBuffer.BufferFromShape(MyElements(j), CDbl(FormSKPM.tbSetOffset.Text))
                        j = j + 1
errnocreateBuffer:
                Next i
            End If
    End If
    
    On Error GoTo ErrExit
    
    Set MyEnum = myAttach.Scan(myFilter)
        While MyEnum.MoveNext
            Select Case MyEnum.Current.Type
                Case msdElementTypeShape
                    Set Corridors(UBound(Corridors)) = MyEnum.Current
                    ReDim Preserve Corridors(UBound(Corridors) + 1)
            End Select
        Wend
    ReDim Preserve Corridors(UBound(Corridors) - 1)
    
    j = 0
    i = (UBound(Candidates) + 1)
    For i = i To (i + UBound(Corridors))
        ReDim Preserve Candidates(UBound(Candidates) + 1)
        Set Candidates(i) = CreateBuffer.BufferFromShape(Corridors(j), CDbl(FormSKPM.tbRegionOffset.Text))
        j = j + 1
    Next i
    
ErrExit:
 '   ReDim Preserve Candidates(UBound(Candidates) - 1)
    Erase MyElements
    Erase Corridors
End Sub

Attribute VB_Name = "FormSKPM"
Attribute VB_Base = "0{0D4AFD81-ACD0-4D14-8BE0-5865EB0A00F1}{A28F36FA-A322-4FF9-BE47-11FD42BF1350}"
Attribute VB_GlobalNameSpace = False
Attribute VB_Creatable = False
Attribute VB_PredeclaredId = True
Attribute VB_Exposed = False
Attribute VB_TemplateDerived = False
Attribute VB_Customizable = False

Private Sub botton_setProfile_Click()
    CommandState.StartLocate New LCE_SpanProfiles
End Sub

Private Sub button_SelectLevelsForOffset_Click()
    ufLevelsForOffset.Show
End Sub

Private Sub button_SelectNoLevel_Click()
    ufListNoLevels.Show
End Sub

Private Sub cbCells_Change()
    If cbCells.Value = True Then
        ufCells.Show vbModeless
    ElseIf cbCells.Value = False Then
        Unload ufCells
    End If
End Sub
Private Sub cbCreateRegion_Click()
    If FormSKPM.cmbReference.Text = "" And FormSKPM.cbUseCorridor.Value = True Then MsgBox "Укажите Reference"
    If FormSKPM.cbSetOffset.Value = True Then
        CommandState.StartPrimitive New PCE_GetDistance, True
    Else:
        CommandState.StartPrimitive New PCE_Create_region, True
    End If
End Sub
Private Sub cbFilterOn_Change()
    Dim l As Integer ' Отступ слева
    Dim r As Integer ' Отступ справа
    l = 5
    r = 5
    
    If cbFilterOn.Value = True Then
        Frame1.Visible = True
        Frame3.left = Frame1.width + l + r - 4
        MultiPage1.width = Frame1.width + Frame3.width + l + 2 * r - 4
        FormSKPM.width = MultiPage1.width + l + r
    ElseIf cbFilterOn.Value = False Then
        Frame1.Visible = False
        Frame3.left = l - 2
        MultiPage1.width = Frame3.width + l + r
        FormSKPM.width = MultiPage1.width + l + r
    End If
End Sub

Private Sub cbFilters_Change()
    FormSKPM.lbGroup.Clear
    Initialization.IniGroup FormSKPM.cbFilters.Text
End Sub

Private Sub cbNoLevel_Change()
'    If cbNoLevel.Value = True Then
'        ufListNoLevels.Show
'    Else
'        ufListNoLevels.Hide
'    End If
End Sub

Private Sub cbOpenXLS_Click()
    GModul.LoadSett
    If IsCellLibraryAttached = False Then MsgBox "Подключите библиотеку Cell", vbOKOnly
End Sub
Private Sub cmDrawVertical_Click()
    CommandState.StartPrimitive New PCE_DrawVerticalETL, True
End Sub

Private Sub CommandButton1_Click()
    myWorkbook.Close
End Sub

Private Sub CommandButton2_Click()
         frmExample.Show vbModeless

End Sub





Private Sub CommandButton3_Click()
    CommandState.StartLocate New LCE_Get_Angle_of_segment
End Sub

Private Sub Frame5_Click()

End Sub

Private Sub lbGroup_Change()
    Initialization.InitialiseForm FormSKPM.lbObjCell, "1_FeatureBasic", FormSKPM.cbFilters.Text
End Sub

Private Sub lbObjCell_Change()
    SetActivSet lbObjCell.Text, "Placement_1"  ' Установка слоя, загрузка изображения и проверка на поворот
    'Lnumber.Caption = Initialization.GetNumber(FormSKPM.lbObjCell.Text, "Placement_1") ' Определение номера Cell по имени
End Sub
Private Sub lbObjCell_DblClick(ByVal Cancel As MSForms.ReturnBoolean)
    CommandState.StartDefaultCommand
    Unload ufPlaceText ' Закрывать окно текста, если было включено
    ufPlacement.Show vbModeless
    IniPlacementForm lbObjCell.Text
    
End Sub
Private Sub lbObLine_Click()
    CommandState.StartPrimitive New PCE_PlaceLineString, True
End Sub


Private Sub UserForm_Initialize()
    cbFilters.AddItem "Все"
    cbFilters.AddItem "По группам"
    cbFilters.AddItem "По типу"
    InitializationReference
    
    Initialization.IniListBoxView FormSKPM.cbListViewPROFILE
    Initialization.IniListBoxView FormSKPM.cbListViewTOP
End Sub

Private Sub UserForm_QueryClose(Cancel As Integer, CloseMode As Integer)
    On Error Resume Next
        Unload ufDrawParall_2
        Unload ufPlacement
        Unload ufPlaceText
        myWorkbook.Close
        MsgBox "пока"
    Err.Clear
End Sub

Attribute VB_Name = "GModul"
Declare Function mdlDialog_fileOpen Lib "stdmdlbltin.dll" (ByVal _
    fileName As String, ByVal rFileH As Long, ByVal _
    resourceId As Long, ByVal suggestedFileName As String, _
    ByVal filterString As String, ByVal defaultDirectory As String, _
    ByVal titleString As String) As Long
Public PathXls As String
Public MyShape As ShapeElement
Public Offs As Double ' Оффсет для параллельных линий
Public SetRegionPoint As Point3d ' Точка внутри региона при задании офсета от дороги
Public ProfileVerteces() As Point3d ' Вертексы профиля

Sub LoadSett()
    Dim strFname As String
    Dim lngfhandle As Long
    Dim lngrid As Long
    Dim retVal As Long
    strFname = Space(255)
    LoadPreset PathXls
    If PathXls = "" Then
            retVal = mdlDialog_fileOpen(strFname, lngfhandle, lngrid, "", "*.xls", _
                                        Application.Path, "Открыть файл настроек")
        Select Case retVal
            Case 0 'Open
                On Error Resume Next
                    PathXls = left(strFname, InStr(1, strFname, Chr(0)) - 1)
                    MsgBox "Загружены настройки из файла:" & vbCr & strFname
                    Set myWorkbook = myExcel.Workbooks.Open(PathXls)
                    Set myExcel = Nothing
                    Initialization.InitialiseForm FormSKPM.lbObjCell, "1_FeatureBasic", FormSKPM.cbFilters.Text
                    'Initialization.InitialiseForm FormSKPM.lbObLine, "Placement_1", "PlaceLineString", "PlaceLineString"
                    If Err.Number <> 0 Then MsgBox Err.Description
                Err.Clear
            Case 1 'Cancel
                MsgBox "Файл не выделен"
        End Select
    Else
            Set myWorkbook = myExcel.Workbooks.Open(PathXls)
            Set myExcel = Nothing
            Initialization.InitialiseForm FormSKPM.lbObjCell, "1_FeatureBasic", FormSKPM.cbFilters.Text
    End If
End Sub
Sub LoadPreset(SetPath As String)
    Dim settingsFname As String
    Dim SetFile As Long
        SetFile = FreeFile
    On Error GoTo errOpen
        settingsFname = left(Application.Path, InStr(1, Application.Path, "\Program\") - 1) & "\Workspace\System\vba\skpm_settings.txt"
        Open settingsFname For Input As #SetFile
        While EOF(SetFile) = False
            Line Input #SetFile, SetPath
            Debug.Print SetPath
        Wend
        Close #SetFile
        Debug.Print settingsFname
errOpen:
End Sub
Sub Main()
    FormSKPM.Show vbModeless
    inizializeNoLevel ufListNoLevels.lbNoLevels
    inizializeNoLevel ufLevelsForOffset.lbLevels
End Sub
Sub offsetPlus()
    ufDrawParall_2.tbOffset.Text = CDbl(ufDrawParall_2.tbOffset.Text) + CDbl(ufDrawParall_2.tbStepOffset.Text)
End Sub
Sub offsetMinus()
    ufDrawParall_2.tbOffset.Text = CDbl(ufDrawParall_2.tbOffset.Text) - CDbl(ufDrawParall_2.tbStepOffset.Text)
'    Offs = Offs - CDbl(ufDrawParall_2.tbStepOffset.Text)
End Sub
 Sub inizializeNoLevel(MyListBox As ListBox)
    Dim MyLevel As Level
    Dim MyLevelName() As String
    ReDim MyLevelName(0)
    Dim MadeChange As Boolean
    Dim i As Integer
    Dim tmpName As String
    
        MyListBox.Clear
    For Each MyLevel In ActiveDesignFile.Levels
        MyLevelName(UBound(MyLevelName)) = MyLevel.Name
        ReDim Preserve MyLevelName(UBound(MyLevelName) + 1)
    Next
        ReDim Preserve MyLevelName(UBound(MyLevelName) - 1)
        
        MadeChange = True
        While MadeChange = True
            MadeChange = False
            For i = LBound(MyLevelName) To UBound(MyLevelName) - 1
                If StrComp(MyLevelName(i), MyLevelName(i + 1)) = 1 Then
                    tmpName = MyLevelName(i)
                    MyLevelName(i) = MyLevelName(i + 1)
                    MyLevelName(i + 1) = tmpName
                    MadeChange = True
                End If
            Next i
        Wend
        For i = LBound(MyLevelName) To UBound(MyLevelName)
            MyListBox.AddItem MyLevelName(i)
        Next i
End Sub

Attribute VB_Name = "GetAngle"
Option Explicit

Function GAngle(pSt As Point3d, pEnd As Point3d) As Double
Dim dAng As Double
Dim Angel As Double
Dim ang As Double
Dim dx As Double
Dim dy As Double
dx = pEnd.X - pSt.X
dy = pEnd.Y - pSt.Y
If dy <> 0 Then
    ang = Atn(dx / dy)
    If dx >= 0 And dy > 0 Then
        dAng = ang
    ElseIf dx >= 0 And dy < 0 Then
        dAng = ang + Pi
    ElseIf dx < 0 And dy < 0 Then
        dAng = ang + Pi
    ElseIf dx < 0 And dy > 0 Then
        dAng = ang + 2 * Pi
    End If
ElseIf dy = 0 Then

    If dx > 0 Then
        dAng = Pi / 2
    ElseIf dx < 0 Then
        dAng = 3 * Pi / 4
    End If
End If
Angel = Pi / 2 - dAng
GAngle = Angel
End Function

Attribute VB_Name = "GetIntersectionShape"
Option Explicit

Sub GetIntersectionShape(Element1 As ShapeElement, Element2 As ShapeElement)
'    Element1 -коридор
'    Element2 - контур дороги
    Dim MyEnum As ElementEnumerator
    Dim MShape As ShapeElement
    Dim ResultShape As ShapeElement
    On Error GoTo notshape
    Set MyEnum = Element1.GetIntersectionShapes(Element2)
    While MyEnum.MoveNext
        Select Case MyEnum.Current.Type
            Case msdElementTypeComplexShape
                Set MShape = ComplexShapeToShape.ComplexShapeToShape(MyEnum.Current)
        End Select
    Wend
    
        Set ResultShape = CreateShapeElement1(Element2, MShape.GetVertices, msdFillModeNotFilled)
        
        ActiveModelReference.AddElement ResultShape
        ResultShape.Redraw
        
        ActiveModelReference.RemoveElement Element2
        Element2.Redraw
        Set MyShape = ResultShape
notshape:
End Sub

Attribute VB_Name = "GetPictureCell"
Option Explicit

Sub DrawCellPreview(CellName As String)
    Dim width As Long
    Dim height As Long
    Dim MyCell As CellElement
    Dim Op As Point3d
    
    width = PointsToPixelsX(ufCells.CellPreview.width)
    height = PointsToPixelsY(ufCells.CellPreview.height)
    
    Set MyCell = CreateCellElement3(CellName, Op, True)
    Set ufCells.CellPreview.Picture = MyCell.GetPicture(width * 0.62, height * 0.62, True)

End Sub

Attribute VB_Name = "Initialization"
Option Explicit
    Public myExcel As New Excel.Application
    Public myWorkbook As Excel.Workbook
    Public CurrSheet As Worksheet
    Public ObjRow As Long
    Public Type TxtStyle
        Font As String
        height As Long
        Weight As Long
        just As String
    End Type
    Public Type SpecLineStyle
        LSt As LineStyle ' Стиль левой линии
        LClr As Long ' Цвет левой линии
        LGw As Long ' Глобальная тольщина левой линии
        CSt As LineStyle ' Стиль центральной линии
        CClr As Long ' Цвет центральной линии
        CGw As Long ' Глобальная толщина центральной линии
        RSt As LineStyle ' Стиль правой линии
        RClr As Long ' Цвет правой линии
        RGw As Long ' Глобальная толщина правой линии
    End Type
    Public sls As SpecLineStyle
    Public TxtSt As TxtStyle
' --------------------------------------------------------------------
    Type SpecLineSt
        offset As Double      ' Оффсет
        Style As LineStyle  ' Стиль линии
        Color As Long       ' Цвет линии
        GWidth As Long      ' Глобальная толщина
        Level As String     ' Слой
    End Type
 ' ---------------------------------------------------------------------
    Type AltSymb
        Level As Level
        Color As Long
        Style As LineStyle
        Weight As Long
    End Type
 ' ------------------------------------------------------------------------
    Public PointAdjst As String ' Параметры привязки вектора к ТЛС
    Public LineParam() As String ' Массив для параметров на отдельную линию / Параметры привязки к точке
    Public CloseShape As Boolean ' Условие зымыкание контура

Sub InitialiseForm(LstBox As ListBox, sheet As String, group As String)
'LstBox - какой список инициализировать
'Sheet - имя листа, с которого считывать объекты
'TypeOfEl - какой тип объектов инициализировать
'Group - по какой группе фильтровать
    Dim curRow As Long
    Dim GrupCol As Long ' Поле Группа
    curRow = 2 ' Начинать поиск со сторой строки
    Set CurrSheet = myWorkbook.Worksheets(sheet)
    LstBox.Clear
    
    Select Case group
        Case "По группам"
            iniFormbyType "Groups", 3
        Case "По типу"
            iniFormbyType "Placement_1", 4
        Case "Все"
            FormSKPM.lbGroup.Clear
            While CurrSheet.Cells(curRow, 2) <> ""
                LstBox.AddItem CurrSheet.Cells(curRow, 2)
                curRow = curRow + 1
            Wend
    End Select
End Sub
Sub iniFormbyType(sheet As String, collum As Integer) ' Инициализирует список объектов в зависимости от круппы
    Dim Mysheet As Worksheet
    Set Mysheet = myWorkbook.Worksheets(sheet)
    Dim curRow As Long
    curRow = 2 ' Начинать поиск со сторой строки
    
    While CurrSheet.Cells(curRow, 2) <> ""
        If Mysheet.Cells(curRow, collum) = FormSKPM.lbGroup.List(FormSKPM.lbGroup.ListIndex) Then
            FormSKPM.lbObjCell.AddItem CurrSheet.Cells(curRow, 2)
        End If
    curRow = curRow + 1
    Wend
End Sub
Sub IniGroup(group As String) ' Инициализация списка групп
        Dim curRow As Long
        curRow = 2 ' Начинать поиск со сторой строки
        FormSKPM.lbObjCell.Clear
    Select Case group
        Case "По группам"
            IniGroupType 3, "Groups"
        Case "По типу"
            IniGroupType 4, "Placement_1"
        Case "Все"
            FormSKPM.lbGroup.Clear
            While CurrSheet.Cells(curRow, 2) <> ""
                FormSKPM.lbObjCell.AddItem CurrSheet.Cells(curRow, 2)
                curRow = curRow + 1
            Wend
    End Select
End Sub
Sub IniGroupType(collum As Integer, sheet As String) ' Инициализирует список групп
    Dim Mysheet As Worksheet
    Set Mysheet = myWorkbook.Worksheets(sheet)
    Dim i As Long
    Dim bool As Boolean
    Dim curRow As Long
    curRow = 2
    While Mysheet.Cells(curRow, collum) <> ""
        Do
            For i = 0 To FormSKPM.lbGroup.ListCount - 1
                If Mysheet.Cells(curRow, collum) = FormSKPM.lbGroup.List(i, 0) Then
                    Exit Do
                End If
            Next i
        FormSKPM.lbGroup.AddItem Mysheet.Cells(curRow, collum)
        Loop While bool = True
    curRow = curRow + 1
    Wend
End Sub

Sub SetActivSet(Object As String, sheet As String) ' Устанавливает активным слой
    Dim curRow As Long
    Dim TypeCol As Long ' Поле типа элемента
    Dim srange As Range
    curRow = 2 ' Начинать поиск со сторой строки
    TypeCol = 4 ' Номер колонки, содержащий тип объекта
    Set CurrSheet = myWorkbook.Worksheets(sheet)
    Set srange = CurrSheet.Columns(2).Find(Object, LookIn:=xlValues)
    curRow = srange.Row
    On Error Resume Next
    'Do While CurrSheet.Cells(curRow, 2) <> ""
        'If CurrSheet.Cells(curRow, 2) = Object Then
            ActiveSettings.Level = CheckLevel(CurrSheet.Cells(curRow, 5))
            'GetPictureCell.DrawCellPreview CurrSheet.Cells(curRow, 11)
           ' If CurrSheet.Cells(curRow, TypeCol) = TypeOfEl2 Then
             '   FormSKPM.cbRotate.Value = True
           ' ElseIf CurrSheet.Cells(curRow, TypeCol) = TypeOfEl1 Then
               ' FormSKPM.cbRotate.Value = False
           ' End If
            'Exit Do
        'End If
        'curRow = curRow + 1
    'Loop
    Err.Clear
End Sub
Function CheckLevel(LevelName As String) As Level ' Проверка файла на наличие слоя, если нет, то создает
    On Error Resume Next
    Set CheckLevel = ActiveDesignFile.Levels(LevelName)
    If Err.Number <> 0 Then
        Set CheckLevel = ActiveDesignFile.AddNewLevel(LevelName)
    End If
    Err.Clear
End Function
Function CheckLineStyle(LineStyleName As String) As LineStyle ' Проверка файла на наличия стиля линии, если нет, то использует по слою
    On Error Resume Next
        Set CheckLineStyle = ActiveDesignFile.LineStyles(LineStyleName)
        If Err.Number <> 0 Then
            Set CheckLineStyle = ByLevelLineStyle
        End If
    Err.Clear
End Function
Sub InitializationGroup(TypyOfEl As String, sheet As String, Filter As String)
    Set CurrSheet = myWorkbook.Worksheets(sheet)
End Sub
Function GetNumber(Name As String, sheet As String) As String ' Возращает номер Cell по назаванию
     Dim curRow As Long
     Dim srange As Range
     Set srange = CurrSheet.Columns(2).Find(Name, LookIn:=xlValues)
     curRow = srange.Row
     Set CurrSheet = myWorkbook.Worksheets(sheet)
     Do While CurrSheet.Cells(curRow, 2) <> ""
        If CurrSheet.Cells(curRow, 2) = Name Then
            GetNumber = CurrSheet.Cells(curRow, 11)
            Exit Do
        End If
        curRow = curRow + 1
    Loop
End Function
Sub IniPlacementForm(Object As String) ' Инициализация формы Размещения (Placment)
    Dim MyRange As Range
    
    ufPlacement.ObjName.Caption = Object
    
'    ufPlacement.cbPlYes_1.Value = False
'    ufPlacement.cbPlYes_2.Value = False
'    ufPlacement.cbPlYes_3.Value = False
    
    ufPlacement.ButtonDraw_1.Enabled = False
    ufPlacement.ButtonDraw_2.Enabled = False
    ufPlacement.ButtonDraw_3.Enabled = False
    
    Set CurrSheet = myWorkbook.Worksheets("Placement_1")
    Set MyRange = CurrSheet.Columns(2).Find(Object, LookIn:=xlValues)
    ObjRow = MyRange.Row
    ufPlacement.lPlace_1 = CurrSheet.Cells(ObjRow, 4)
    ufPlacement.lSymb_1 = CurrSheet.Cells(ObjRow, 6)
    IniPlacementCb "Placement_1", CurrSheet.Cells(ObjRow, 4)
    
    Set CurrSheet = myWorkbook.Worksheets("Placement_2")
    ufPlacement.lPlace_2 = CurrSheet.Cells(ObjRow, 4)
    ufPlacement.lSymb_2 = CurrSheet.Cells(ObjRow, 6)
    IniPlacementCb "Placement_2", CurrSheet.Cells(ObjRow, 4)
    
    Set CurrSheet = myWorkbook.Worksheets("Placement_3")
    ufPlacement.lPlace_3 = CurrSheet.Cells(ObjRow, 4)
    ufPlacement.lSymb_3 = CurrSheet.Cells(ObjRow, 6)
    IniPlacementCb "Placement_3", CurrSheet.Cells(ObjRow, 4)
    
End Sub
Sub IniPlacementCb(sheet As String, Place As String)
    If Place <> "" And Place <> "N/A" Then
        Select Case Mid(sheet, 11)
            Case "1"
                ufPlacement.ButtonDraw_1.Enabled = True
            Case "2"
                ufPlacement.ButtonDraw_2.Enabled = True
            Case "3"
                ufPlacement.ButtonDraw_3.Enabled = True
        End Select
    ElseIf Place = "" Or Place = "N/A" Then
        Placements.RunPlacements ufPlacement.lPlace_1.Caption, "Placement_1"
    End If
End Sub
Sub IniTextStyle(RowObj As Long, sheet As String) 'Инициализация параметров текста
    Dim Mysheet As Worksheet
    Dim Param As String
    Dim i As Integer ' Положение курсoра при поиске ","
    Dim j As Integer
    
    Set Mysheet = myWorkbook.Worksheets(sheet)
    Param = Mysheet.Cells(RowObj, 7)
    i = InStr(1, Param, ",")
    
    TxtSt.Font = Mid(Param, 4, i - 4)
    For j = 1 To 2
        Select Case j
            Case 1
                TxtSt.height = CLng(Mid(Param, i + 1, (InStr(i + 1, Param, ",") - i) - 1))
                i = InStr(i + 1, Param, ",")
            Case 2
                TxtSt.Weight = CLng(Mid(Param, i + 1, (InStr(i + 1, Param, ",") - i) - 1))
                i = InStr(i + 1, Param, ",")
        End Select
    Next j
        TxtSt.just = Mid(Param, i + 1, Len(Param))
End Sub
Function TxtJust(just As String) As String ' Функция возвращает значение привязки MSD по сокращенному параметру
    Select Case just
        Case "LB"
            TxtJust = msdTextJustificationLeftBottom
    End Select
End Function

Sub IniTxtDomen(RowObj As Long, sheet As String) ' Инициализация текстового домена
    Dim Mysheet As Worksheet
    Dim Param As String
    Dim i As Integer
    Dim txtDomen() As String
    Set Mysheet = myWorkbook.Worksheets(sheet)
    Param = Mysheet.Cells(RowObj, 8)
    ufPlaceText.cbTxtDomen.Clear
    Select Case Param
        Case ""
            ufPlaceText.cbTxtDomen.Enabled = False
            Exit Sub
        Case "N/A"
            ufPlaceText.cbTxtDomen.Enabled = False
            Exit Sub
        Case Is <> ""
            txtDomen = Split(Param, ";")
            For i = 0 To UBound(txtDomen)
                ufPlaceText.cbTxtDomen.AddItem txtDomen(i)
            Next i
    End Select
        ufPlaceText.cbTxtDomen.ListIndex = 0
End Sub
Sub IniSpecLine(Param As String)
    Dim i As Integer
    Dim aLineP As String
    i = InStr(1, Param, ";")
    aLineP = left(Param, i - 1)
    If CDbl(left(Param, 2)) > 0 Then

    End If
End Sub
Sub iniLine(Param As String)

Dim i As Integer
Dim l As Integer

l = Len(Param)
i = InStr(1, Param, ":")
    Select Case left(Param, 1)
        Case Param = 0
            sls.CSt = ActiveDesignFile.LineStyles(Mid(Param, i + 1, (InStr(i + 1, Param, ":") - i + 1)))
        Case Param > 0
            sls.RSt = ActiveDesignFile.LineStyles(Mid(Param, i + 1, (InStr(i + 1, Param, ":") - i + 1)))
        Case Param < 0
            sls.LSt = ActiveDesignFile.LineStyles(Mid(Param, i + 1, (InStr(i + 1, Param, ":") - i + 1)))
    End Select
    i = InStr(i + 1, Param, ":")
End Sub

Sub InitializationReference()
Dim MyModel As ModelReference
Dim myAttachment As Attachment
Set MyModel = ActiveDesignFile.DefaultModelReference
    For Each myAttachment In MyModel.Attachments
        Debug.Print myAttachment.AttachName
        FormSKPM.cmbReference.AddItem myAttachment.AttachName
        myAttachment.LogicalName = myAttachment.AttachName
    Next
   If FormSKPM.cmbReference.ListCount > 0 Then FormSKPM.cmbReference.ListIndex = 0
End Sub

Sub IniListBoxView(LBox As ComboBox)
    Dim i As Integer
    For i = 1 To 8
        LBox.AddItem "View" & " " & i
    Next i
End Sub

Attribute VB_Name = "LCE_CutRoad"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Implements ILocateCommandEvents
Dim CutShape As ClosedElement
Private SelElement As Element ' Элемент, по которому будет обрезаться дорога
Private Sub ILocateCommandEvents_Accept(ByVal Element As Element, Point As Point3d, ByVal View As View)
    Dim oElement() As Element
    Dim MyEnum As ElementEnumerator
    Dim rShape As ComplexShapeElement 'Результирующий shape
    Dim cut As Boolean
    ReDim oElement(0)
    Set oElement(0) = Element
    Set MyEnum = CutShape.GetDifferenceShapesFromRegion(oElement, Nothing, msdFillModeFilled)
    While MyEnum.MoveNext
        Select Case MyEnum.Current.Type
            Case msdElementTypeComplexShape
                If cut = False Then ActiveModelReference.RemoveElement CutShape
                Set rShape = MyEnum.Current
                rShape.FillMode = msdFillModeNotFilled
                ActiveModelReference.AddElement rShape
                rShape.Redraw
                cut = True
        End Select
    Wend
    Set CutShape = rShape
    
End Sub

Private Sub ILocateCommandEvents_Cleanup()

End Sub

Private Sub ILocateCommandEvents_Dynamics(Point As Point3d, ByVal View As View, ByVal DrawMode As MsdDrawingMode)

End Sub

Private Sub ILocateCommandEvents_LocateFailed()

End Sub

Private Sub ILocateCommandEvents_LocateFilter(ByVal Element As Element, Point As Point3d, Accepted As Boolean)
    Accepted = False
    If Element.IsShapeElement Or Element.IsComplexShapeElement Then
        Set SelElement = Element
        Accepted = True
        ActiveModelReference.SelectElement Element, True
        ShowCommand "Стыковка дорог"
        ShowPrompt "Подтвердите выделение нажав левой кнопкой мыши"
    End If
End Sub

Private Sub ILocateCommandEvents_LocateReset()
    CommandState.StartDefaultCommand
    Unload ufDrawParall_2
End Sub

Private Sub ILocateCommandEvents_Start()
    Set CutShape = MyShape
    BoolSpLineCut = False
End Sub

Attribute VB_Name = "LCE_Get_Angle_of_segment"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private SelShape As ShapeElement
Private Verteces() As Point3d
Private MyElement As Element
Private Angel As Double
Private myTxt As TextElement
Private txt As String
Public txtDomen_LCE As String
Public txtLevel_LCE As String
Private bool As Boolean
Private RotationMatrix As Matrix3d
Private txtPoint As Point3d

Implements ILocateCommandEvents

Private Sub ILocateCommandEvents_Accept(ByVal Element As Element, Point As Point3d, ByVal View As View)
    If bool = False Then
        bool = True
       ' CommandState.StartDynamics
    ElseIf bool = True Then
        Set myTxt = CreateTextElement1(Nothing, txt, Point, RotationMatrix)
        myTxt.TextStyle.Font = ActiveDesignFile.Fonts(TxtSt.Font)
        myTxt.TextStyle.height = TxtSt.height
        myTxt.TextStyle.width = TxtSt.Weight
        myTxt.TextStyle.Justification = Initialization.TxtJust(TxtSt.just)
        myTxt.Level = ActiveDesignFile.Levels.Find(txtLevel_LCE)
        ActiveModelReference.AddElement myTxt
        myTxt.Redraw
        bool = False
        CommandState.StartLocate Me
    End If
End Sub

Private Sub ILocateCommandEvents_Cleanup()
    
End Sub

Private Sub ILocateCommandEvents_Dynamics(Point As Point3d, ByVal View As View, ByVal DrawMode As MsdDrawingMode)
    Dim Vertices() As Point3d
    Dim startIndex As Integer
    Dim stMarker As EllipseElement
    Dim endMarker As EllipseElement
    
    Dim Sc As Point3d
    Sc.X = 1
    Sc.Y = 1
    Sc.Z = 1
    
    If txtDomen_LCE = "" Or txtDomen_LCE = "N/A" Then
            txt = ufPlaceText.tbText.Text
        Else
            txt = ufPlaceText.cbTxtDomen.Text & " " & ufPlaceText.tbAddText.Text
    End If
    
    If bool = False Then
    
    On Error GoTo done
    Verteces = MyElement.AsVertexList.GetVertices
    startIndex = MyElement.AsVertexList.GetClosestSegment(Point)

done:
      '  startIndex = SelShape.AsVertexList.GetClosestSegment(Point)
    
        Set stMarker = CreateEllipseElement2(Nothing, Verteces(startIndex), 0.4, 0.4, Matrix3dIdentity)
        stMarker.LineWeight = 0
        stMarker.Color = 2
        stMarker.Redraw DrawMode
        Set endMarker = CreateEllipseElement2(Nothing, Verteces(startIndex + 1), 0.4, 0.4, Matrix3dIdentity)
        endMarker.LineWeight = 0
        endMarker.Color = 3
        endMarker.Redraw DrawMode
        
        Angel = GetAngle.GAngle(Verteces(startIndex), Verteces(startIndex + 1))
        If Angel > Pi * 0.5 Or Angel < -Pi * 0.5 Then
            Angel = Angel + Pi
            startIndex = startIndex + 1
        End If
        
        RotationMatrix = Matrix3dFromAxisAndRotationAngle(2, Angel)
        Set myTxt = CreateTextElement1(Nothing, txt, Verteces(startIndex), RotationMatrix)
        myTxt.TextStyle.Font = ActiveDesignFile.Fonts(TxtSt.Font)
        myTxt.TextStyle.height = TxtSt.height
        myTxt.TextStyle.width = TxtSt.Weight
        myTxt.TextStyle.Justification = Initialization.TxtJust(TxtSt.just)
        myTxt.Level = ActiveDesignFile.Levels.Find(txtLevel_LCE)
        myTxt.Redraw DrawMode
        
     ElseIf bool = True Then
        txtPoint = Point
        Set myTxt = CreateTextElement1(Nothing, txt, txtPoint, RotationMatrix)
        myTxt.TextStyle.Font = ActiveDesignFile.Fonts(TxtSt.Font)
        myTxt.TextStyle.height = TxtSt.height
        myTxt.TextStyle.width = TxtSt.Weight
        myTxt.TextStyle.Justification = Initialization.TxtJust(TxtSt.just)
        myTxt.Level = ActiveDesignFile.Levels.Find(txtLevel_LCE)
        myTxt.Redraw DrawMode
        
     End If
End Sub

Private Sub ILocateCommandEvents_LocateFailed()
    CommandState.StartLocate Me
  '  bool = True
'    If bool = True Then
'        Set myTxt = CreateTextElement1(Nothing, txt, txtPoint, RotationMatrix)
'        myTxt.TextStyle.Font = ActiveDesignFile.Fonts(TxtSt.Font)
'        myTxt.TextStyle.height = TxtSt.height
'        myTxt.TextStyle.width = TxtSt.Weight
'        myTxt.TextStyle.Justification = Initialization.TxtJust(TxtSt.just)
'        myTxt.Level = ActiveDesignFile.Levels.Find(txtLevel_LCE)
'        ActiveModelReference.AddElement myTxt
'        myTxt.Redraw
'    End If
End Sub

Private Sub ILocateCommandEvents_LocateFilter(ByVal Element As Element, Point As Point3d, Accepted As Boolean)
    Accepted = False
'    If Element.IsShapeElement Then
'        Set SelShape = Element
'        Accepted = True
'        CommandState.StartDynamics
'    End If
    If Element.IsShapeElement Or Element.IsComplexShapeElement Or Element.IsLineElement Then
        Set MyElement = Element
        Accepted = True
        Select Case Element.Type
            Case msdElementTypeShape
                RemapLevel Element, ufPlaceText.cbTxtDomen.Text
            Case msdElementTypeComplexShape
                RemapLevel Element, ufPlaceText.cbTxtDomen.Text
                Set MyElement = ComplexShapeToShape.ComplexShapeToShape(Element.AsComplexShapeElement)
        End Select
        CommandState.StartDynamics
    End If
End Sub

Private Sub ILocateCommandEvents_LocateReset()
    CommandState.StartDefaultCommand
End Sub

Private Sub ILocateCommandEvents_Start()

End Sub

Private Sub RemapLevel(Element As Element, txt As String)
    
    Dim nameLv As String
    
    Select Case txt
        Case "R.D."
            nameLv = "Department road RD"
        Case "R.N."
            nameLv = "National road RN"
        Case "A."
            nameLv = "Highway A"
        Case "V.C."
            nameLv = "Commune road VC"
        Case "C.O."
            nameLv = "Commune road VC"
        Case "C.R."
            nameLv = "Commune road VC"
        Case "C.E."
            nameLv = "Commune road VC"
        Case "R.F."
            nameLv = "Commune road VC"
        Case "C.V."
            nameLv = "Commune road VC"
        Case "C.V.O."
            nameLv = "Commune road VC"
        Case "RIVIERE"
            Exit Sub
        Case "RUISSEAU"
            Exit Sub
        Case "S.N.C.F."
            Exit Sub
    End Select
    Element.Level = Initialization.CheckLevel(nameLv)  '  ActiveModelReference.Levels(nameLv)
    Element.Rewrite
    Element.Redraw
End Sub

Attribute VB_Name = "LCE_PlaceCellRotate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements ILocateCommandEvents
Private bPoint As Point3d ' Точка вставки Cell

Private Sub ILocateCommandEvents_Accept(ByVal Element As Element, Point As Point3d, ByVal View As View)
    Dim MyCell As CellElement
    Dim CellName As String
    
    Dim RotationMatrix As Matrix3d
    Dim Sc As Point3d
    Sc.X = 1
    Sc.Y = 1
    Sc.Z = 1
    CellName = Initialization.GetNumber(FormSKPM.lbObjCell.Text, "Placement_1")
    RotationMatrix = Matrix3dFromAxisAndRotationAngle(2, GetAngle.GAngle(bPoint, Point))
    Set MyCell = CreateCellElement2(CellName, bPoint, Sc, True, RotationMatrix)
    MyCell.Level = ActiveDesignFile.Levels.Find(ActiveSettings.Level.Name)
    ActiveModelReference.AddElement MyCell
    MyCell.Redraw
    CommandState.StopDynamics
    
End Sub

Private Sub ILocateCommandEvents_Cleanup()

End Sub

Private Sub ILocateCommandEvents_Dynamics(Point As Point3d, ByVal View As View, ByVal DrawMode As MsdDrawingMode)
    Dim MyCell As CellElement
    Dim CellName As String
    
    Dim RotationMatrix As Matrix3d
    Dim Sc As Point3d
    Sc.X = 1
    Sc.Y = 1
    Sc.Z = 1
    CellName = Initialization.GetNumber(FormSKPM.lbObjCell.Text, "Placement_1")
    RotationMatrix = Matrix3dFromAxisAndRotationAngle(2, GetAngle.GAngle(bPoint, Point))
    Set MyCell = CreateCellElement2(CellName, bPoint, Sc, True, RotationMatrix)
    MyCell.Level = ActiveDesignFile.Levels.Find(ActiveSettings.Level.Name)
    MyCell.Redraw DrawMode
    
End Sub

Private Sub ILocateCommandEvents_LocateFailed()
    CommandState.StartLocate Me
End Sub

Private Sub ILocateCommandEvents_LocateFilter(ByVal Element As Element, Point As Point3d, Accepted As Boolean)
    If Element.IsValid Then
    Accepted = True
    bPoint = Point
    CommandState.StartDynamics
    End If
End Sub

Private Sub ILocateCommandEvents_LocateReset()
    CommandState.StartDefaultCommand
End Sub

Private Sub ILocateCommandEvents_Start()
   CommandState.EnableAccuSnap
End Sub

Attribute VB_Name = "LCE_SpanProfiles"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private Verteces() As Point3d

Implements ILocateCommandEvents

Private Sub ILocateCommandEvents_Accept(ByVal Element As Element, Point As Point3d, ByVal View As View)
    Dim i As Integer
    ProfileVerteces = Element.AsLineElement.GetVertices
    ufSpanProfiles.Show vbModeless
    ufSpanProfiles.lbSpanProfiles.Clear
        For i = 1 To UBound(ProfileVerteces)
            ufSpanProfiles.lbSpanProfiles.AddItem i & "-" & (i + 1)
        Next i
    CommandState.StartDynamics
End Sub

Private Sub ILocateCommandEvents_Cleanup()

End Sub

Private Sub ILocateCommandEvents_Dynamics(Point As Point3d, ByVal View As View, ByVal DrawMode As MsdDrawingMode)
    Dim MyLine As LineElement
    Dim i As Integer
    Dim v As Integer
    
    
    For i = 1 To ufSpanProfiles.lbSpanProfiles.ListCount
        If ufSpanProfiles.lbSpanProfiles.Selected(i - 1) Then
            Set MyLine = CreateLineElement2(Nothing, Verteces(i - 1), Verteces(i))
            MyLine.Redraw DrawMode
        End If
    Next i
    v = Point.X
End Sub

Private Sub ILocateCommandEvents_LocateFailed()
    
End Sub

Private Sub ILocateCommandEvents_LocateFilter(ByVal Element As Element, Point As Point3d, Accepted As Boolean)
Accepted = False

If Element.IsLineElement = True Then
    Accepted = True
End If
End Sub

Private Sub ILocateCommandEvents_LocateReset()
    CommandState.StartDefaultCommand
End Sub

Private Sub ILocateCommandEvents_Start()

End Sub

Attribute VB_Name = "PCE_Create_region"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Implements IPrimitiveCommandEvents
Private aCandidates() As Element
Private oElement As Element
Private Sub IPrimitiveCommandEvents_Cleanup()

End Sub
Private Sub IPrimitiveCommandEvents_DataPoint(Point As Point3d, ByVal View As View)
    Dim myFilter As New ElementScanCriteria
    Dim MyEnum As ElementEnumerator
    Dim shEnum As ElementEnumerator
    Dim myReg As ComplexElement
    Dim MyShape As ShapeElement
    Dim myRegion As LineElement
    Dim i As Long
    Dim j As Integer ' Счетчик для слоев, которые не должны учитываться
    Dim MyLevel As Level
    Dim MyPoint As Point3d ' Точка задающая регион
    
    myFilter.ExcludeAllTypes
    myFilter.IncludeType msdElementTypeLineString
    myFilter.IncludeType msdElementTypeShape
    myFilter.IncludeType msdElementTypeComplexShape
    myFilter.IncludeType msdElementTypeLine
    
    If FormSKPM.cbNoLevel.Value = True Then
        myFilter.ExcludeAllLevels
'            For Each MyLevel In ActiveDesignFile.Levels
                For j = 1 To ufListNoLevels.lbNoLevels.ListCount
                    If Not ufListNoLevels.lbNoLevels.Selected(j - 1) Then
                        myFilter.IncludeLevel ActiveDesignFile.Levels.Find(ufListNoLevels.lbNoLevels.List(j - 1))
                    End If
                Next j
'            Next
    End If
    
    
    Set MyEnum = ActiveModelReference.Scan(myFilter)
            While MyEnum.MoveNext
            If MyEnum.Current.Level.IsDisplayedInView(ActiveDesignFile.Views.Item(1)) = True Then
                Set aCandidates(i) = MyEnum.Current
                i = i + 1
                ReDim Preserve aCandidates(i)
            End If
        Wend
    ReDim Preserve aCandidates(i - 1)
    
    MyPoint = Point
    If FormSKPM.cbUseCorridor.Value = True Then GetCorridorsFromReference aCandidates ' Включение коридоров из референса
    If FormSKPM.cbSetOffset.Value = True Then MyPoint = SetRegionPoint ' Если указывается оффсет вручную. то точка региона прделевается по вектору взятия дистанции
    
    Set oElement = GetFloodBoundary(aCandidates, Nothing, MyPoint, , False, -1, msdFillModeFilled)
    If oElement Is Nothing Then MsgBox "Регион не построен", vbOKOnly
    Set myReg = oElement
    Set shEnum = myReg.GetSubElements
        While shEnum.MoveNext
            Set myRegion = shEnum.Current
        Wend
    Set MyShape = CreateShapeElement1(Nothing, myRegion.GetVertices, msdFillModeNotFilled)
    ActiveModelReference.AddElement MyShape
    MyShape.Redraw
    CommandState.StartDefaultCommand
    If FormSKPM.cbDeletInitialElement.Value = True Then DeletInitialLine MyShape
    ActiveDesignFile.Views(View.Index).Redraw
End Sub

Private Sub IPrimitiveCommandEvents_Dynamics(Point As Point3d, ByVal View As View, ByVal DrawMode As MsdDrawingMode)

End Sub

Private Sub IPrimitiveCommandEvents_Keyin(ByVal Keyin As String)

End Sub

Private Sub IPrimitiveCommandEvents_Reset()
    'Myform.InputFence CDbl(Myform.tbOffset.Text), Myform.cmbCell.Text
End Sub

Private Sub IPrimitiveCommandEvents_Start()
    ReDim aCandidates(0)
End Sub

Private Sub DeletInitialLine(Element As Element)
    Dim myFilter As New ElementScanCriteria
    Dim MyEnum As ElementEnumerator
    Dim MyLevel As Level
    Dim MyLine As LineElement
    Dim iPoint() As Point3d
  '  Set MyLevel = Shape.Level
    
    myFilter.ExcludeAllTypes
    myFilter.ExcludeAllLevels
    myFilter.IncludeType msdElementTypeLine
    myFilter.IncludeType msdElementTypeLineString
    myFilter.IncludeLevel ActiveDesignFile.Levels.Find(Element.Level.Name)
    
    Set MyEnum = ActiveModelReference.Scan(myFilter)
        While MyEnum.MoveNext
            Set MyLine = MyEnum.Current
            iPoint = MyLine.AsIntersectableElement.GetIntersectionPointsOnIntersector(Element, Matrix3dIdentity)
            If UBound(iPoint) >= 0 Then
                ActiveModelReference.RemoveElement MyLine
            End If
        Wend
    
End Sub

Attribute VB_Name = "PCE_DrawVerticalETL"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IPrimitiveCommandEvents

Private Sub IPrimitiveCommandEvents_Cleanup()

End Sub

Private Sub IPrimitiveCommandEvents_DataPoint(Point As Point3d, ByVal View As View)

End Sub

Private Sub IPrimitiveCommandEvents_Dynamics(Point As Point3d, ByVal View As View, ByVal DrawMode As MsdDrawingMode)
    Dim HitCircle As EllipseElement ' Прицел
    Dim VertLine As LineElement
    Dim Hpoint As Point3d ' Верхняя точка
        
    Hpoint.X = Point.X
    Hpoint.Y = Point.Y
    Hpoint.Z = Point.Z + 5
    
    Set HitCircle = CreateEllipseElement2(Nothing, Point, 2, 2, Matrix3dIdentity)
    HitCircle.Color = 3
    HitCircle.Redraw DrawMode
    Set VertLine = CreateLineElement2(Nothing, Point, Hpoint)
    VertLine.Redraw DrawMode
    
End Sub

Private Sub IPrimitiveCommandEvents_Keyin(ByVal Keyin As String)

End Sub

Private Sub IPrimitiveCommandEvents_Reset()
    CommandState.StartDefaultCommand
End Sub

Private Sub IPrimitiveCommandEvents_Start()
    CommandState.StartDynamics
End Sub

Attribute VB_Name = "PCE_DynamicParall"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents
Dim mView As View
Dim boolset As Boolean
Dim CentreLine() As Point3d
Dim v As Long ' Количество вертексов осевой линии
Dim LLine() As Point3d
Dim RLine() As Point3d
Dim offset() As Double ' Значения офсетов для каждого вертекса
Dim LinStyle(0 To 2) As SpecLineSt
Dim SplitLineParam() As String
Dim LineOn(0 To 2) As Boolean ' Ключи для отрисовки линий (0 - левая, 1- центральная, 2- правая)

Private Sub IPrimitiveCommandEvents_Cleanup()

End Sub
Private Sub IPrimitiveCommandEvents_DataPoint(Point As Point3d, ByVal View As View)
    If boolset = False Then
            v = 0
            CentreLine(v) = Point
            offset(v) = Offs
            v = v + 1
            ReDim Preserve CentreLine(v)
            ReDim Preserve LLine(v)
            ReDim Preserve RLine(v)
            ReDim Preserve offset(v)
            CommandState.StartDynamics
            boolset = True
        Else
            CentreLine(v) = Point
            offset(v) = Offs
            v = v + 1
            ReDim Preserve CentreLine(v)
            ReDim Preserve LLine(v)
            ReDim Preserve RLine(v)
            ReDim Preserve offset(v)
    End If
    Placements.MoveView Point, View
  '  frmExample.Show vbModeless
    Set mView = View
End Sub
Private Sub IPrimitiveCommandEvents_Dynamics(Point As Point3d, ByVal View As View, ByVal DrawMode As MsdDrawingMode)
    Dim LLs As LineElement
    Dim RLs As LineElement
    Dim Cline As LineElement
    
    Dim IPl As Point3d
    Dim IPr As Point3d
    Dim p(0 To 3) As Point3d
    
    Offs = CDbl(ufDrawParall_2.tbOffset.Text)
    

    CentreLine(v) = Point
    p(0) = Perpendicular(CentreLine(v - 1), CentreLine(v), offset(v - 1))(0)
    p(1) = Perpendicular(CentreLine(v - 1), CentreLine(v), offset(v - 1))(1)
    p(2) = Perpendicular(CentreLine(v - 1), CentreLine(v), Offs)(2)
    p(3) = Perpendicular(CentreLine(v - 1), CentreLine(v), Offs)(3)
    LLine(v) = p(2)
    RLine(v) = p(3)
        If v = 1 Then
                p(0) = Perpendicular(CentreLine(v - 1), CentreLine(v), Offs)(0)
                p(1) = Perpendicular(CentreLine(v - 1), CentreLine(v), Offs)(1)
                LLine(v - 1) = p(0)
                RLine(v - 1) = p(1)
            ElseIf v > 1 Then
                IPl = IntersectionLines(LLine(v - 2), LLine(v - 1), p(0), p(2))
                IPr = IntersectionLines(RLine(v - 2), RLine(v - 1), p(1), p(3))
                LLine(v - 1) = IPl
                RLine(v - 1) = IPr
        End If
        
        If LineOn(0) = True Then
            Set LLs = CreateLineElement1(Nothing, LLine)
            ApplySettingsLines LLs, 0
            LLs.Color = 0
            LLs.Redraw DrawMode
        End If
                
        If LineOn(1) = True Then
            Set Cline = CreateLineElement1(Nothing, CentreLine)
            ApplySettingsLines Cline, 1
            Cline.Color = 0
            Cline.Redraw DrawMode
        End If
        
        If LineOn(2) = True Then
            Set RLs = CreateLineElement1(Nothing, RLine)
            ApplySettingsLines RLs, 2
            RLs.Color = 0
            RLs.Redraw DrawMode
        End If
            
        
''''    If ufDrawParall.cbLeft.Value = True Then
''''        Set LLs = CreateLineElement1(Nothing, LLine)
''''        LLs.Color = CDbl(ufDrawParall.tbColorL.Text)
''''        LLs.Redraw DrawMode
''''    End If
''''
''''    If ufDrawParall.cbRight.Value = True Then
''''        Set RLs = CreateLineElement1(Nothing, RLine)
''''        RLs.Color = CDbl(ufDrawParall.tbColorR.Text)
''''        RLs.Redraw DrawMode
''''    End If
''''
''''    If ufDrawParall.cbCentral.Value = True Then
''''        Set Cline = CreateLineElement1(Nothing, CentreLine)
''''        Cline.Color = CDbl(ufDrawParall.tbColorC.Text)
''''        Cline.Redraw DrawMode
''''    End If


End Sub
Private Sub IPrimitiveCommandEvents_Keyin(ByVal Keyin As String)
    Select Case UCase(Keyin)
        Case "SAS"
            Debug.Print "Undo"
            v = v - 1
            ReDim Preserve CentreLine(v)
            ReDim Preserve LLine(v)
            ReDim Preserve RLine(v)
            ReDim Preserve offset(v)
    End Select

End Sub
Private Sub IPrimitiveCommandEvents_Reset()
    Dim line As LineElement
    Dim LL As LineElement
    Dim RL As LineElement
    'Dim Shape As ShapeElement
    Dim i As Integer
    Dim j As Integer
    Dim k As Integer
    Dim n As Integer
    Dim buf As ShapeElement
    v = v - 1
    ReDim Preserve CentreLine(v)
    ReDim Preserve LLine(v)
    ReDim Preserve RLine(v)
    ReDim Preserve offset(v)
    k = v
    j = 0
    n = 0
    Dim sh() As Point3d
    ReDim sh(0)
    For i = 0 To ((2 * v) + 1)
        ReDim Preserve sh(i)
            If j <= v Then
                If (LineOn(0) = True And LineOn(1) = True) Or LineOn(0) = True Then
                    sh(i) = LLine(j)
                    j = j + 1
                ElseIf LineOn(0) = False Then
                    sh(i) = CentreLine(j)
                    j = j + 1
                End If
                
            Else
                If LineOn(2) = True Then
                    sh(i) = RLine(k)
                    k = k - 1
                ElseIf LineOn(2) = False Then
                    sh(i) = CentreLine(k)
                    k = k - 1
                End If
        End If
    Next i
        If CloseShape = True Then
            Set MyShape = CreateShapeElement1(Nothing, sh)
            Do
                If LineOn(n) = True Then Exit Do
                n = n + 1
            Loop While n < 2
            ApplySettingsLines MyShape, n
            
            ActiveModelReference.AddElement MyShape
            MyShape.FillMode = msdFillModeNotFilled
            MyShape.Redraw
            
            CutRoad MyShape
            
            ActiveDesignFile.Views(mView.Index).Redraw
            
            CommandState.StartDefaultCommand
            CommandState.StartLocate New LCE_CutRoad
            ShowCommand "Стыковка дорог"
            ShowPrompt "Выделите дорогу к которой пристыковаться или Reset"
        ElseIf CloseShape = False Then
            If LineOn(0) = True Then
                Set LL = CreateLineElement1(Nothing, LLine)
                ApplySettingsLines LL, 0
                ActiveModelReference.AddElement LL
                LL.Redraw
            End If
        
            If LineOn(2) = True Then
                Set RL = CreateLineElement1(Nothing, RLine)
                ApplySettingsLines RL, 2
                ActiveModelReference.AddElement RL
                RL.Redraw
            End If
        
            If LineOn(1) = True Then
                Set line = CreateLineElement1(Nothing, CentreLine)
                ApplySettingsLines line, 0
                ActiveModelReference.AddElement line
                line.Redraw
            End If
            CommandState.StartDefaultCommand
        End If
End Sub
Private Sub IPrimitiveCommandEvents_Start()
    ReDim CentreLine(0)
    ReDim LLine(0)
    ReDim RLine(0)
    ReDim offset(0)
    CommandState.EnableAccuSnap
    InitializationSpecLineParam
    If LineOn(0) = True And LineOn(2) = True Then
        Offs = LinStyle(2).offset
    ElseIf LineOn(0) = True Then
        Offs = Abs(LinStyle(0).offset)
    ElseIf LineOn(2) = True Then
        Offs = Abs(LinStyle(2).offset)
    End If
End Sub
Private Sub InitializationSpecLineParam()
    Dim j As Integer
    
    For j = 0 To UBound(LineParam)
        SplitLineParam = Split(LineParam(j), ":")
        Select Case left(LineParam(j), 1)
            Case "-"
                SetLineStyle LinStyle(0)
                LineOn(0) = True
            Case "0"
                SetLineStyle LinStyle(1)
                LineOn(1) = True
            Case "1" To "9"
                SetLineStyle LinStyle(2)
                LineOn(2) = True
        End Select
   Next j
End Sub
Private Sub SetLineStyle(LS As SpecLineSt)
        Dim n As Integer
            Do
                If LineOn(n) = True Then Exit Do
                n = n + 1
            Loop While n < 2
            
    LS.offset = CDbl(SplitLineParam(0))
        
        If SplitLineParam(1) = "BL" Then
            Set LS.Style = ByLevelLineStyle
        Else
            Set LS.Style = Initialization.CheckLineStyle(SplitLineParam(1))
        End If
        If SplitLineParam(2) = "BL" Then
            LS.Color = ByLevelColor
        Else
            LS.Color = SplitLineParam(2)
        End If
    LS.GWidth = SplitLineParam(3)
        If SplitLineParam(4) = "Sim" Then
            LS.Level = LinStyle(n).Level ' Берет слой из левой линии
        Else
            Initialization.CheckLevel (SplitLineParam(4))
            LS.Level = SplitLineParam(4)
        End If
        
End Sub

Private Sub ApplySettingsLines(MyLine As Element, num As Integer)
    MyLine.Color = LinStyle(num).Color
    MyLine.Level = ActiveDesignFile.Levels.Find(LinStyle(num).Level) ' Initialization.CheckLevel(SplitLineParam(4))
    Set MyLine.LineStyle = LinStyle(num).Style
End Sub

'-----функция поиска точки пересечения прямых, заданных соответствующими парами координат-----

Function IntersectionLines(PP1 As Point3d, PP2 As Point3d, PP3 As Point3d, PP4 As Point3d) As Point3d
    Dim k1 As Double
    Dim k2 As Double
    Dim b1 As Double
    Dim b2 As Double
    If PP1.X = PP2.X And PP3.X = PP4.X And PP2.X = PP3.X Then
            IntersectionLines.X = PP2.X
            IntersectionLines.Y = PP2.Y
        ElseIf PP1.Y = PP2.Y And PP3.Y = PP4.Y And PP2.Y = PP3.Y Then
                IntersectionLines.X = PP2.X
                IntersectionLines.Y = PP2.Y
        ElseIf PP3.X = PP4.X Then
            k1 = (PP2.Y - PP1.Y) / (PP2.X - PP1.X)
            b1 = (PP1.Y * PP2.X - PP2.Y * PP1.X) / (PP2.X - PP1.X)
            IntersectionLines.X = PP3.X
            IntersectionLines.Y = k1 * PP3.X + b1
        ElseIf PP1.X = PP2.X Then
            k2 = (PP4.Y - PP3.Y) / (PP4.X - PP3.X)
            b2 = (PP3.Y * PP4.X - PP4.Y * PP3.X) / (PP4.X - PP3.X)
            IntersectionLines.X = PP1.X
            IntersectionLines.Y = k2 * PP1.X + b2
        Else
            k1 = (PP2.Y - PP1.Y) / (PP2.X - PP1.X)
            b1 = (PP1.Y * PP2.X - PP2.Y * PP1.X) / (PP2.X - PP1.X)
            k2 = (PP4.Y - PP3.Y) / (PP4.X - PP3.X)
            b2 = (PP3.Y * PP4.X - PP4.Y * PP3.X) / (PP4.X - PP3.X)
            IntersectionLines.X = (b2 - b1) / (k1 - k2)
            IntersectionLines.Y = (k1 * (b2 - b1) / (k1 - k2)) + b1
    End If
End Function
Function Perpendicular(PP1 As Point3d, PP2 As Point3d, Of As Double) As Point3d()
    Dim PP(0 To 3) As Point3d ' Искомые точки перпендикуляров
                                ' 0 - 1 - перпендикуляры на начале отрезка Лево - Право, соответственно
                                ' 2 - 3 - перпендикуляры на конце отрезка Лево - Право, соответственно
    Dim Ax As Double
    Dim Ay As Double
    Dim vLine As Vector3d   ' Отрезок осевой линии
    Dim vRoad As Vector3d   ' Точка сдвига относительно осевой линии
    Ax = PP2.X - PP1.X
    Ay = PP2.Y - PP1.Y
    vLine = Vector3dFromXY(Ax, Ay)
    vRoad = Vector3dUnitPerpendicularXY(vLine)
    vRoad = Vector3dScale(vRoad, Of)
    PP(0).X = Vector3dGetComponent(vRoad, 0) + PP1.X
    PP(0).Y = Vector3dGetComponent(vRoad, 1) + PP1.Y
    PP(2).X = Vector3dGetComponent(vRoad, 0) + PP2.X
    PP(2).Y = Vector3dGetComponent(vRoad, 1) + PP2.Y
    vRoad = Vector3dScale(vRoad, -1)
    PP(1).X = Vector3dGetComponent(vRoad, 0) + PP1.X
    PP(1).Y = Vector3dGetComponent(vRoad, 1) + PP1.Y
    PP(3).X = Vector3dGetComponent(vRoad, 0) + PP2.X
    PP(3).Y = Vector3dGetComponent(vRoad, 1) + PP2.Y
    Perpendicular = PP
End Function
Private Sub CutRoad(Road As ShapeElement)
    Dim myFilter As New ElementScanCriteria
    Dim myAttach As Attachment
    
    If FormSKPM.cmbReference.ListCount > 0 Then
    
        Set myAttach = ActiveDesignFile.DefaultModelReference.Attachments(FormSKPM.cmbReference.ListIndex + 1)
        
        myFilter.ExcludeAllTypes
        myFilter.ExcludeAllLevels
        
        myFilter.IncludeType msdElementTypeShape
        myFilter.IncludeLevel myAttach.Levels.FindByNumber(CLng(FormSKPM.tbLevelCorridor.Text))
        
        Set MyEnum = myAttach.Scan(myFilter)
            While MyEnum.MoveNext
                Select Case MyEnum.Current.Type
                    Case msdElementTypeShape
                        GetIntersectionShape.GetIntersectionShape CreateBuffer.BufferFromShape(MyEnum.Current, CDbl(FormSKPM.tbRegionOffset.Text)), Road
                End Select
            Wend
    End If

End Sub

Attribute VB_Name = "PCE_GetDistance"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Dim bool As Boolean
Dim sPoint As Point3d
Dim ePoint As Point3d

Implements IPrimitiveCommandEvents

Private Sub IPrimitiveCommandEvents_Cleanup()

End Sub

Private Sub IPrimitiveCommandEvents_DataPoint(Point As Point3d, ByVal View As View)
    Dim Ax As Double
    Dim Ay As Double
    Dim dist As Vector3d
    
    If bool = False Then
        sPoint = Point
        bool = True
    ElseIf bool = True Then
        ePoint = Point
        Ax = ePoint.X - sPoint.X
        Ay = ePoint.Y - sPoint.Y
        dist = Vector3dFromXY(Ax, Ay)
        dist = Vector3dScale(dist, 1.2)
        SetRegionPoint.X = sPoint.X + Vector3dGetComponent(dist, 0)
        SetRegionPoint.Y = sPoint.Y + Vector3dGetComponent(dist, 1)
        FormSKPM.tbSetOffset.Text = Round(Point3dDistance(sPoint, ePoint), 2)
        CommandState.StartPrimitive New PCE_Create_region, True
      '  CommandState.StartDefaultCommand
    End If
End Sub

Private Sub IPrimitiveCommandEvents_Dynamics(Point As Point3d, ByVal View As View, ByVal DrawMode As MsdDrawingMode)
    
    If bool = False Then
        sPoint = Point
    ElseIf bool = True Then
        ePoint = Point
    End If
    
End Sub

Private Sub IPrimitiveCommandEvents_Keyin(ByVal Keyin As String)

End Sub

Private Sub IPrimitiveCommandEvents_Reset()
     
End Sub

Private Sub IPrimitiveCommandEvents_Start()
    CommandState.StartDynamics
End Sub

Attribute VB_Name = "PCE_PlaceCell"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private CellName As String
Implements IPrimitiveCommandEvents

Private Sub IPrimitiveCommandEvents_Cleanup()

End Sub

Private Sub IPrimitiveCommandEvents_DataPoint(Point As Point3d, ByVal View As View)
    Dim MyCell As CellElement
    Set MyCell = CreateCellElement3(CellName, Point, True)
    MyCell.Level = ActiveDesignFile.Levels.Find(ActiveSettings.Level.Name)
    ActiveModelReference.AddElement MyCell
    MyCell.Redraw
End Sub

Private Sub IPrimitiveCommandEvents_Dynamics(Point As Point3d, ByVal View As View, ByVal DrawMode As MsdDrawingMode)
    Dim MyCell As CellElement
    Set MyCell = CreateCellElement3(CellName, Point, True)
    MyCell.Redraw DrawMode
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
    CommandState.StartDynamics
    CellName = Initialization.GetNumber(ufCells.lbObjCell.Text, "Placement_1")
End Sub

Attribute VB_Name = "PCE_PlaceCellRotate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private bPoint As Point3d ' Точка вставки Cell
Private FirstPoint As Boolean ' Проверка на первую точку
Private CellName As String
Implements IPrimitiveCommandEvents

Private Sub IPrimitiveCommandEvents_Cleanup()

End Sub

Private Sub IPrimitiveCommandEvents_DataPoint(Point As Point3d, ByVal View As View)
Dim MyCell As CellElement
    
Dim RotationMatrix As Matrix3d
Dim Sc As Point3d
Sc.X = 1
Sc.Y = 1
Sc.Z = 1

If FirstPoint = False Then
    bPoint = Point
    FirstPoint = True
Else
    RotationMatrix = Matrix3dFromAxisAndRotationAngle(2, GetAngle.GAngle(bPoint, Point))
    Set MyCell = CreateCellElement2(CellName, bPoint, Sc, True, RotationMatrix)
    MyCell.Level = ActiveDesignFile.Levels.Find(ActiveSettings.Level.Name)
    ActiveModelReference.AddElement MyCell
    MyCell.Redraw
    CommandState.StopDynamics
    FirstPoint = False
End If
End Sub

Private Sub IPrimitiveCommandEvents_Dynamics(Point As Point3d, ByVal View As View, ByVal DrawMode As MsdDrawingMode)
    Dim MyCell As CellElement
    
    Dim RotationMatrix As Matrix3d
    Dim Sc As Point3d
    Sc.X = 1
    Sc.Y = 1
    Sc.Z = 1

If FirstPoint = False Then
    bPoint = Point
    Set MyCell = CreateCellElement2(CellName, bPoint, Sc, True, Matrix3dIdentity)
    MyCell.Redraw DrawMode
Else
    RotationMatrix = Matrix3dFromAxisAndRotationAngle(2, GetAngle.GAngle(bPoint, Point))
    Set MyCell = CreateCellElement2(CellName, bPoint, Sc, True, RotationMatrix)
    MyCell.Redraw DrawMode
    'ActiveModelReference.AddElement MyCell
    'MyCell.Redraw
End If
End Sub

Private Sub IPrimitiveCommandEvents_Keyin(ByVal Keyin As String)

End Sub

Private Sub IPrimitiveCommandEvents_Reset()
    CommandState.StartDefaultCommand
End Sub

Private Sub IPrimitiveCommandEvents_Start()
    CellName = Initialization.GetNumber(ufCells.lbObjCell.Text, "Placement_1")
    CommandState.EnableAccuSnap
    CommandState.StartDynamics
End Sub

Attribute VB_Name = "PCE_PlaceLineString"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IPrimitiveCommandEvents
Private LineVert() As Point3d
Dim boolset As Boolean

Private Sub IPrimitiveCommandEvents_Cleanup()

End Sub

Private Sub IPrimitiveCommandEvents_DataPoint(Point As Point3d, ByVal View As View)
    Dim MyShape As ShapeElement
    
    If boolset = False Then
        LineVert(UBound(LineVert)) = Point
        CommandState.StartDynamics
        boolset = True
    ElseIf boolset = True Then
        LineVert(UBound(LineVert)) = Point
'            If UBound(LineVert) > 2 And Point3dDistance(Point, LineVert(0)) = 0 Then ' Проверка на замыкание, если текущая точка совпадает с первой, то создается Shape
'                Set myShape = CreateShapeElement1(Nothing, LineVert)
'                ActiveModelReference.AddElement myShape
'                myShape.Redraw
'            End If
    End If
ReDim Preserve LineVert(UBound(LineVert) + 1)
Placements.MoveView Point, View
End Sub

Private Sub IPrimitiveCommandEvents_Dynamics(Point As Point3d, ByVal View As View, ByVal DrawMode As MsdDrawingMode)
    Dim LineString As LineElement
    LineVert(UBound(LineVert)) = Point
    Set LineString = CreateLineElement1(Nothing, LineVert)
    LineString.Redraw DrawMode
End Sub

Private Sub IPrimitiveCommandEvents_Keyin(ByVal Keyin As String)
     Select Case UCase(Keyin)
        Case "SAS"
            ReDim Preserve LineVert(UBound(LineVert) - 1)
    End Select
End Sub

Private Sub IPrimitiveCommandEvents_Reset()
    Dim LineString As LineElement
  '  Dim oCurve As BsplineCurveElement
  '  Dim curve As New InterpolationCurve
    ReDim Preserve LineVert(UBound(LineVert) - 1)
    
    Set LineString = CreateLineElement1(Nothing, LineVert)
    
  '  curve.SetFitPoints LineVert
  '  Set oCurve = CreateBsplineCurveElement2(Nothing, curve)
  '  ActiveModelReference.AddElement oCurve
  '  oCurve.Redraw
    
    ActiveModelReference.AddElement LineString
    LineString.Redraw
    Placements.PointAdjusmentOff
    CommandState.StartDefaultCommand
End Sub

Private Sub IPrimitiveCommandEvents_Start()
    ReDim LineVert(0)
    CommandState.EnableAccuSnap
End Sub

Attribute VB_Name = "PCE_Place_TextRotation"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private myTxt As TextElement
Private txt As String
Private bool As Boolean
Private bPoint As Point3d
'Public MySeetTxt As String
Public txtDomen As String
Public txtLevel As String
'Private Mysheet As Worksheet
Implements IPrimitiveCommandEvents
Private Sub IPrimitiveCommandEvents_Cleanup()
End Sub
Private Sub IPrimitiveCommandEvents_DataPoint(Point As Point3d, ByVal View As View)
    Dim RotationMatrix As Matrix3d
    Dim Sc As Point3d
    Sc.X = 1
    Sc.Y = 1
    Sc.Z = 1
    If bool = False Then
        bPoint = Point
        bool = True
            If ufPlaceText.cbTxtRotation.Value = False Then
                Set myTxt = CreateTextElement1(Nothing, txt, Point, Matrix3dIdentity)
                myTxt.TextStyle.Font = ActiveDesignFile.Fonts(TxtSt.Font)
                myTxt.TextStyle.height = TxtSt.height
                myTxt.TextStyle.width = TxtSt.Weight
                myTxt.TextStyle.Justification = Initialization.TxtJust(TxtSt.just)
                myTxt.Level = ActiveDesignFile.Levels.Find(txtLevel)
                ActiveModelReference.AddElement myTxt
                myTxt.Redraw
                CommandState.StopDynamics
                bool = False
                CommandState.StartDynamics
            End If
    ElseIf bool = True Then
        RotationMatrix = Matrix3dFromAxisAndRotationAngle(2, GetAngle.GAngle(bPoint, Point))
        Set myTxt = CreateTextElement1(Nothing, txt, bPoint, RotationMatrix)
        myTxt.TextStyle.Font = ActiveDesignFile.Fonts(TxtSt.Font)
        myTxt.TextStyle.height = TxtSt.height
        myTxt.TextStyle.width = TxtSt.Weight
        myTxt.TextStyle.Justification = Initialization.TxtJust(TxtSt.just)
        myTxt.Level = ActiveDesignFile.Levels.Find(txtLevel)
        ActiveModelReference.AddElement myTxt
        myTxt.Redraw
        CommandState.StopDynamics
        bool = False
        CommandState.StartDynamics
    End If
End Sub

Private Sub IPrimitiveCommandEvents_Dynamics(Point As Point3d, ByVal View As View, ByVal DrawMode As MsdDrawingMode)
    Dim RotationMatrix As Matrix3d
    Dim Sc As Point3d
    Sc.X = 1
    Sc.Y = 1
    Sc.Z = 1
    
        If txtDomen = "" Or txtDomen = "N/A" Then
            txt = ufPlaceText.tbText.Text
        Else
            txt = ufPlaceText.cbTxtDomen.Text
        End If

    If bool = False Then
        Set myTxt = CreateTextElement1(Nothing, txt, Point, Matrix3dIdentity)
        myTxt.TextStyle.Font = ActiveDesignFile.Fonts(TxtSt.Font)
        myTxt.TextStyle.height = TxtSt.height
        myTxt.TextStyle.width = TxtSt.Weight
        myTxt.TextStyle.Justification = Initialization.TxtJust(TxtSt.just)
        myTxt.Level = ActiveDesignFile.Levels.Find(txtLevel)
        myTxt.Redraw DrawMode
    ElseIf bool = True Then
        RotationMatrix = Matrix3dFromAxisAndRotationAngle(2, GetAngle.GAngle(bPoint, Point))
        Set myTxt = CreateTextElement1(Nothing, txt, bPoint, RotationMatrix)
        myTxt.TextStyle.Font = ActiveDesignFile.Fonts(TxtSt.Font)
        myTxt.TextStyle.height = TxtSt.height
        myTxt.TextStyle.width = TxtSt.Weight
        myTxt.TextStyle.Justification = Initialization.TxtJust(TxtSt.just)
        myTxt.Level = ActiveDesignFile.Levels.Find(txtLevel)
        myTxt.Redraw DrawMode
    End If
End Sub
Private Sub IPrimitiveCommandEvents_Keyin(ByVal Keyin As String)

End Sub
Private Sub IPrimitiveCommandEvents_Reset()
    CommandState.StartDefaultCommand
    Unload ufPlaceText
    'Unload ufDrawParall ' Закрыть окно отрисовки параллельных линий
End Sub
Private Sub IPrimitiveCommandEvents_Start()
    CommandState.EnableAccuSnap
    CommandState.StartDynamics
   ' Set Mysheet = myWorkbook.Worksheets(MySeetTxt)
End Sub

Attribute VB_Name = "PCE_Point"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Dim MyLine As LineElement

Implements IPrimitiveCommandEvents

Private Sub IPrimitiveCommandEvents_Cleanup()

End Sub

Private Sub IPrimitiveCommandEvents_DataPoint(Point As Point3d, ByVal View As View)
    Set MyLine = CreateLineElement2(Nothing, Point, Point)
    ActiveModelReference.AddElement MyLine
    MyLine.Redraw
End Sub

Private Sub IPrimitiveCommandEvents_Dynamics(Point As Point3d, ByVal View As View, ByVal DrawMode As MsdDrawingMode)
    Set MyLine = CreateLineElement2(Nothing, Point, Point)
    MyLine.Redraw DrawMode
End Sub

Private Sub IPrimitiveCommandEvents_Keyin(ByVal Keyin As String)

End Sub

Private Sub IPrimitiveCommandEvents_Reset()
    Placements.PointAdjusmentOff
    CommandState.StartDefaultCommand
End Sub

Private Sub IPrimitiveCommandEvents_Start()
    CommandState.StartDynamics
    CommandState.EnableAccuSnap
End Sub

Attribute VB_Name = "Placements"
Option Explicit
Public BoolSpLineCut As Boolean
Public BoolNextPl As Boolean
Sub RunPlacements(Plm As String, sheetNum As String)
    Dim myPCEText As New PCE_Place_TextRotation
    Dim myLCEText As New LCE_Get_Angle_of_segment
    Dim PT As Point3d
    Dim Cadtxt As String
    Dim MSheet As Worksheet
 
    Set MSheet = myWorkbook.Worksheets(sheetNum)
    PointAdjst = MSheet.Cells(ObjRow, 14) ' Получение параметров привязки вектора к ТЛС
    PointAdjusmentOff
    Placements.PointAdjustment PointAdjst

    Select Case Plm
        Case "PlaceLineString"
       '    CadInputQueue.SendCommand "PLACE SMARTLINE"
            CommandState.StartPrimitive New PCE_PlaceLineString, True
        Case "PlaceText"    ' Текст
            IniTextStyle ObjRow, sheetNum
           ' myPCEText.MySeetTxt = sheetNum
            myPCEText.txtDomen = MSheet.Cells(ObjRow, 8)
            myPCEText.txtLevel = MSheet.Cells(ObjRow, 5)
            CommandState.StartPrimitive myPCEText ' Передает лист с которого читать параметры
            IniTxtDomen ObjRow, sheetNum
            ufPlaceText.cbTxtRotation.Value = False
            ufPlaceText.Show vbModeless
        Case "PlaceTextRotated"     'Текст с поворотом
            IniTextStyle ObjRow, sheetNum
            myPCEText.txtDomen = MSheet.Cells(ObjRow, 8)
            myPCEText.txtLevel = MSheet.Cells(ObjRow, 5)
            'myPCEText.MySeetTxt = sheetNum
            CommandState.StartPrimitive myPCEText ' Передает лист с которого читать параметры
            IniTxtDomen ObjRow, sheetNum
            ufPlaceText.cbTxtRotation.Value = True
            ufPlaceText.Show vbModeless
        Case "PlaceTextbyElement"
            IniTextStyle ObjRow, sheetNum
            myLCEText.txtDomen_LCE = MSheet.Cells(ObjRow, 8)
            myLCEText.txtLevel_LCE = MSheet.Cells(ObjRow, 5)
            IniTxtDomen ObjRow, sheetNum
            ufPlaceText.cbTxtRotation.Value = False
            ufPlaceText.Show vbModeless
            CommandState.StartLocate myLCEText
        Case "PlaceCell"
            CommandState.StartPrimitive New PCE_PlaceCell, True
        Case "PlaceCellRotated"
            CommandState.StartPrimitive New PCE_PlaceCellRotate, True
        Case "PlacePoint" ' Точка
           CommandState.StartPrimitive New PCE_Point, True
        Case "PlaceShape" ' Замкнутый контур
            CadInputQueue.SendCommand "place shape constrained"
        Case "PlaceShapeOrtho" ' Ортогональный контур
            CadInputQueue.SendCommand "place shape orthogonal"
        Case "PlaceSpecLineConst"
            ' Специальная линия
        Case "PlaceSpecLineVar" ' Специальная линия переменной ширины
            LineParam = Split(MSheet.Cells(ObjRow, 9), ";")
                If MSheet.Cells(ObjRow, 13) = "yes" Then
                    CloseShape = True
                Else
                    CloseShape = False
                End If
            CommandState.StartPrimitive New PCE_DynamicParall, True
            ufDrawParall_2.tbOffset = Offs
            ufDrawParall_2.tbStepOffset = 0.1
            ufDrawParall_2.Show vbModeless
        Case "PlaceHatch"
            ' Заполнение знаками
    End Select
'    Do While BoolNextPl = False
'        On Error Resume Next
'        Debug.Print Err.Number & Err.Description
'    Loop
'    Do While True
'        On Error Resume Next
'        Set oMessage = CadInputQueue.GetInput
'        Debug.Print Err.Number & Err.Description
'            If Err.Description = "Method 'GetInput' of object '_CadInputQueue' failed" Then
'                Exit Do
'                Err.Clear
'                CadInputQueue.SendReset
'                CommandState.StartDefaultCommand
'            End If
'            Select Case oMessage.InputType
'                Case msdCadInputTypeDataPoint
'                    CadInputQueue.SendDataPoint oMessage.Point
'                        If ufPlacement.cbMoveView.Value = True Then
'                            ActiveDesignFile.Views(oMessage.View.Index).Center = PT
'                            ActiveDesignFile.Views(oMessage.View.Index).Redraw
'                        End If
'                Case msdCadInputTypeReset
'                    CadInputQueue.SendReset
'                    If Plm <> "PlaceSpecLineVar" Then   ' Для специальных линий
'                        Exit Sub
'                    Else
'                        If BoolSpLineCut = True Then    ' Проверка условия завершени обрезки
'                            Unload ufDrawParall
'                            Exit Sub
'                        End If
'                    End If
'                Case msdCadInputTypeCommand
'                    Cadtxt = oMessage.CommandKeyin
'                    CadInputQueue.SendCommand Cadtxt
'        End Select
'    Loop
End Sub
Sub MoveView(mPoint As Point3d, mView As View)
    Dim width As Double
    Dim height As Double
    Dim PCentr As Point3d
    
    PCentr = ActiveDesignFile.Views(mView.Index).Center
    width = ActiveDesignFile.Views(mView.Index).Extents.X
    height = ActiveDesignFile.Views(mView.Index).Extents.Y
        If ufPlacement.cbMoveView.Value = True Then
            If Abs(mPoint.X - PCentr.X) >= (width * 0.25) Or Abs(mPoint.Y - PCentr.Y) >= (height * 0.25) Then
                ActiveDesignFile.Views(mView.Index).Center = mPoint
                ActiveDesignFile.Views(mView.Index).Redraw
            Else
                ActiveDesignFile.Views(mView.Index).Redraw
            End If
        Else
            ActiveDesignFile.Views(mView.Index).Redraw
        End If
    
End Sub
Sub PointAdjustment(Param As String) ' Передача параметров по привязки вектора к ТЛС
    LineParam = Split(Param, ";")
    Dim Class As Integer ' К какому классу привязываться
    Dim Point As Integer ' Point closest=0 ; lowest=1; average=2; heighst=3
    Dim Within As Long ' Радиус поиска
        If Param <> "" Then
            Class = CInt(LineParam(0))
            Point = CInt(LineParam(1))
            Within = CInt(LineParam(2))
            CadInputQueue.SendCommand "Mouse Point Adjustment"
            SetCExpressionValue "MpaClass", Class, "TSCAN" ' К какому классу привязываться
            SetCExpressionValue "MpaCalc", Point, "TSCAN" ' Point closest=0 ; lowest=1; average=2; heighst=3
            SetCExpressionValue "MpaWithin", Within, "TSCAN" ' Радиус поиска
            SetCExpressionValue "MpaAdjXy", -1, "TSCAN" 'Включено
            SetCExpressionValue "MpaAdjElev", -1, "TSCAN" 'Включено
        Else
            Exit Sub
        End If
End Sub
Sub PointAdjusmentOff()
On Error Resume Next
    SetCExpressionValue "MpaAdjXy", 0, "TSCAN" 'Выключена привязка по XY
    SetCExpressionValue "MpaAdjElev", 0, "TSCAN" 'Выключено привязка по Z
Err.Clear
End Sub

Attribute VB_Name = "Profiles"
Option Explicit

Sub RotateView()
    Dim MyLine As LineElement
    Dim TopViewIndex As Integer ' Индекс вида сверху
    Dim cPoint As Point3d
    Dim i As Integer
    Dim MyRotation As Matrix3d
    Dim vTransform As Transform3d
    Dim VectorRowZ As Vector3d
    Dim VectorRowX As Vector3d
    Dim pRowX As Point3d
    Dim pRowY As Point3d
    Dim pRowZ As Point3d
    Dim P0 As Point3d
    Dim Ax As Double ' Вспомогательные координаты для оси Y
    Dim Ay As Double
    Dim VectorAxy As Vector3d
    Dim VectorYbyZ As Vector3d
    Dim VectorYbyX As Vector3d
    Dim vExt As Point3d
    
    TopViewIndex = CInt(Right(FormSKPM.cbListViewPROFILE.Text, 1))
    For i = 1 To ufSpanProfiles.lbSpanProfiles.ListCount
        If ufSpanProfiles.lbSpanProfiles.Selected(i - 1) Then

            pRowZ.X = ProfileVerteces(i - 1).X - ProfileVerteces(i).X
            pRowZ.Y = ProfileVerteces(i - 1).Y - ProfileVerteces(i).Y
            pRowZ.Z = ProfileVerteces(i - 1).Z - ProfileVerteces(i).Z
            VectorRowZ = Vector3dFromPoint3d(pRowZ)
            VectorRowX = Vector3dUnitPerpendicularXY(VectorRowZ)
         '   VectorRowX = Vector3dScale(VectorRowX, -1)
            pRowX.X = Vector3dGetComponent(VectorRowX, 0)
            pRowX.Y = Vector3dGetComponent(VectorRowX, 1)
            pRowX.Z = 0

            Ay = pRowZ.Z
            Ax = Sqr(pRowZ.X ^ 2 + pRowZ.Y ^ 2)
            VectorAxy = Vector3dFromXY(Ax, Ay)
            VectorYbyZ = Vector3dUnitPerpendicularXY(VectorAxy)
            VectorYbyX = Vector3dUnitPerpendicularXY(VectorRowX)
            VectorYbyX = Vector3dScale(VectorYbyX, -1)
            VectorYbyX = Vector3dScale(VectorYbyX, Vector3dGetComponent(VectorYbyZ, 0))

            pRowY.X = Vector3dGetComponent(VectorYbyX, 0)
            pRowY.Y = Vector3dGetComponent(VectorYbyX, 1)
            pRowY.Z = Vector3dGetComponent(VectorYbyZ, 1)

            vExt.X = 1000
            vExt.Y = 1000
            vExt.Z = 1000
            P0.X = 10000
            P0.Y = 10000
            P0.Z = 10000

            MyRotation = Matrix3dFromPoint3dRows(pRowX, pRowY, pRowZ)
            ActiveDesignFile.Views(TopViewIndex).SetArea P0, vExt, MyRotation, 0
  '          ActiveDesignFile.Views(TopViewIndex).SetClippingDistanceByPoints P0, vExt
  '          ActiveDesignFile.Views(TopViewIndex).SetToIsometric
    '        vTransform = Transform3dFromMatrix3dAndFixedPoint3d(MyRotation, ProfileVerteces(i))
  '          MyRotation = Matrix3dFromTransform3d(vTransform)
        
            
            
'            ActiveDesignFile.Views(TopViewIndex).Rotation = MyRotation
'            ActiveDesignFile.Views(TopViewIndex).Extents = vExt
'
            
     '       ActiveDesignFile.Views(TopViewIndex).ActiveDepth = 0
       '     ActiveDesignFile.Views(TopViewIndex).Extents = pRowZ
        '    P0.X = ProfileVerteces(i - 1).X * -0.5 + ProfileVerteces(i).X * -0.5
       '     P0.Y = ProfileVerteces(i - 1).Y * -0.5 + ProfileVerteces(i).Y * -0.5
       '     ActiveDesignFile.Views(TopViewIndex).Origin = P0
       '     ActiveDesignFile.Views(TopViewIndex).ActiveDepth = 0
       '     ActiveDesignFile.Views(TopViewIndex).ClipBack = True
'
          

            
            
            
            cPoint.X = 0
            cPoint.Y = 0
            cPoint.Z = 0
            ActiveDesignFile.Views(TopViewIndex).Center = cPoint
            Debug.Print "rowX.X= " & ActiveDesignFile.Views(TopViewIndex).Rotation.RowX.X & vbTab & "inv_rowX.X= " & Matrix3dInverse(ActiveDesignFile.Views(TopViewIndex).Rotation).RowX.X
            Debug.Print "rowX.Y= " & ActiveDesignFile.Views(TopViewIndex).Rotation.RowX.Y & vbTab & "inv_rowX.Y= " & Matrix3dInverse(ActiveDesignFile.Views(TopViewIndex).Rotation).RowX.Y
            Debug.Print "rowX.Z= " & ActiveDesignFile.Views(TopViewIndex).Rotation.RowX.Z & vbTab & "inv_rowX.Z= " & Matrix3dInverse(ActiveDesignFile.Views(TopViewIndex).Rotation).RowX.Z
            Debug.Print "rowY.X= " & ActiveDesignFile.Views(TopViewIndex).Rotation.RowY.X & vbTab & "inv_rowY.X= " & Matrix3dInverse(ActiveDesignFile.Views(TopViewIndex).Rotation).RowY.X
            Debug.Print "rowY.Y= " & ActiveDesignFile.Views(TopViewIndex).Rotation.RowY.Y & vbTab & "inv_rowY.Y= " & Matrix3dInverse(ActiveDesignFile.Views(TopViewIndex).Rotation).RowY.Y
            Debug.Print "rowY.Z= " & ActiveDesignFile.Views(TopViewIndex).Rotation.RowY.Z & vbTab & "inv_rowY.Z= " & Matrix3dInverse(ActiveDesignFile.Views(TopViewIndex).Rotation).RowY.Z
            Debug.Print "rowZ.X= " & ActiveDesignFile.Views(TopViewIndex).Rotation.RowZ.X & vbTab & "inv_rowZ.X= " & Matrix3dInverse(ActiveDesignFile.Views(TopViewIndex).Rotation).RowZ.X
            Debug.Print "rowZ.Y= " & ActiveDesignFile.Views(TopViewIndex).Rotation.RowZ.Y & vbTab & "inv_rowZ.Y= " & Matrix3dInverse(ActiveDesignFile.Views(TopViewIndex).Rotation).RowZ.Y
            Debug.Print "rowZ.Z= " & ActiveDesignFile.Views(TopViewIndex).Rotation.RowZ.Z & vbTab & "inv_rowZ.Z= " & Matrix3dInverse(ActiveDesignFile.Views(TopViewIndex).Rotation).RowZ.Z
            Debug.Print "Origin.X= " & ActiveDesignFile.Views(TopViewIndex).Origin.X
            Debug.Print "Origin.Y= " & ActiveDesignFile.Views(TopViewIndex).Origin.Y
            Debug.Print "Origin.Z= " & ActiveDesignFile.Views(TopViewIndex).Origin.Z
            Debug.Print "Center.X= " & ActiveDesignFile.Views(TopViewIndex).Center.X
            Debug.Print "Center.Y= " & ActiveDesignFile.Views(TopViewIndex).Center.Y
            Debug.Print "Center.Z= " & ActiveDesignFile.Views(TopViewIndex).Center.Z
            Debug.Print ActiveDesignFile.Views(TopViewIndex).DisplaysCamera
            Debug.Print ActiveDesignFile.Views(TopViewIndex).CameraPosition.X
            Debug.Print ActiveDesignFile.Views(TopViewIndex).CameraPosition.Y
            Debug.Print ActiveDesignFile.Views(TopViewIndex).CameraPosition.Z
            Debug.Print ActiveDesignFile.Views(TopViewIndex).CameraTarget.X
            Debug.Print ActiveDesignFile.Views(TopViewIndex).CameraTarget.Y
            Debug.Print ActiveDesignFile.Views(TopViewIndex).CameraTarget.Z
            Debug.Print "Extents.X= " & ActiveDesignFile.Views(TopViewIndex).Extents.X
            Debug.Print "Extents.Y= " & ActiveDesignFile.Views(TopViewIndex).Extents.Y
            Debug.Print "Extents.Z= " & ActiveDesignFile.Views(TopViewIndex).Extents.Z
            Debug.Print "IsIsometric= " & ActiveDesignFile.Views(TopViewIndex).IsIsometric
            
            Debug.Print "*******************************************************************"
            ActiveDesignFile.Views(TopViewIndex).Redraw
            
        End If
    Next i
End Sub

Attribute VB_Name = "frmExample"
Attribute VB_Base = "0{C310940C-9828-46A3-96DE-3CD5D7D31A3B}{29722CB1-2A54-48A8-8411-2EC65620A79B}"
Attribute VB_GlobalNameSpace = False
Attribute VB_Creatable = False
Attribute VB_PredeclaredId = True
Attribute VB_Exposed = False
Attribute VB_TemplateDerived = False
Attribute VB_Customizable = False

Option Explicit

Private Sub TextBox1_Change()

End Sub



Private Sub HookControl1_SentMessage(ByVal uMsg As Long, ByVal wParam As Long, ByVal lParam As Long)

End Sub

' ---------------------------------------------------------------------
'   Notice:
'   Example code provided as-is by LA Solutions Ltd with no guarantee of
'   fitness for purpose.  Use at your own risk.
'   You may use this example code for whatever purpose private or commercial
'   provided that this notice is retained in full.
'
'   http://www.la-solutions.co.uk
'
'   End of notice
' ---------------------------------------------------------------------
'   UserForm_KeyDown event handler
'   See also: UserForm_KeyUp and UserForm_KeyPress
' ---------------------------------------------------------------------
Private Sub UserForm_KeyDown(ByVal keyCode As MSForms.ReturnInteger, ByVal shift As Integer)
    Dim msg                                 As String
    msg = "UserForm_KeyDown keyCode=" & ExplainKeyCode(keyCode)
    lblKeyStroke.Caption = "Key Pressed: " & ExplainKeyCode(keyCode)
    ShowMessage msg, msg, msdMessageCenterPriorityDebug, False
    Debug.Print msg
    Select Case keyCode
        Case 90
            offsetPlus
    End Select
End Sub
' ---------------------------------------------------------------------
Private Function ExplainKeyCode(ByVal keyCode As MSForms.ReturnInteger) As String
    Select Case keyCode
    Case vbKeyLeft
        ExplainKeyCode = "vbKeyLeft (" & CStr(keyCode) & ")"
    Case vbKeyRight
        ExplainKeyCode = "vbKeyRight (" & CStr(keyCode) & ")"
    Case vbKeyUp
        ExplainKeyCode = "vbKeyUp (" & CStr(keyCode) & ")"
    Case vbKeyDown
         ExplainKeyCode = "vbKeyDown (" & CStr(keyCode) & ")"
   Case Else
       ExplainKeyCode = CStr(keyCode)
    End Select
End Function

Attribute VB_Name = "ufDrawParall"
Attribute VB_Base = "0{891E79C9-3A95-4294-93F3-3B8D87D9E17A}{442D729B-2590-4002-8CA3-B077E783A49F}"
Attribute VB_GlobalNameSpace = False
Attribute VB_Creatable = False
Attribute VB_PredeclaredId = True
Attribute VB_Exposed = False
Attribute VB_TemplateDerived = False
Attribute VB_Customizable = False

Option Explicit

Private Sub cmbDraw_Click()
    CommandState.StartPrimitive New PCE_DynamicParall, True
End Sub

Attribute VB_Name = "ufLevelsForOffset"
Attribute VB_Base = "0{B694F0B6-0EDF-44BE-9A2E-DE75B07AFA3A}{EE82C5F9-3C82-47A1-B48D-0909D5FE271A}"
Attribute VB_GlobalNameSpace = False
Attribute VB_Creatable = False
Attribute VB_PredeclaredId = True
Attribute VB_Exposed = False
Attribute VB_TemplateDerived = False
Attribute VB_Customizable = False
Option Explicit
Private Sub button_closeLevelsForOffset_Click()
    ufLevelsForOffset.Hide
End Sub
Private Sub UserForm_QueryClose(Cancel As Integer, CloseMode As Integer)
    Cancel = 1
End Sub

Attribute VB_Name = "ufListNoLevels"
Attribute VB_Base = "0{51C6FC09-A756-4E69-B3C1-63637692939A}{A4FA4821-D50C-43FD-A1C9-71E49950CA24}"
Attribute VB_GlobalNameSpace = False
Attribute VB_Creatable = False
Attribute VB_PredeclaredId = True
Attribute VB_Exposed = False
Attribute VB_TemplateDerived = False
Attribute VB_Customizable = False
Option Explicit
Private Sub button_closeNoLevel_Click()
    ufListNoLevels.Hide
End Sub


Private Sub UserForm_QueryClose(Cancel As Integer, CloseMode As Integer)
   Cancel = 1
End Sub

Attribute VB_Name = "ufPlacement"
Attribute VB_Base = "0{157003E2-397B-418F-9260-A682D6F03337}{0FAE55B2-054C-4745-A38A-CD848AF24CD0}"
Attribute VB_GlobalNameSpace = False
Attribute VB_Creatable = False
Attribute VB_PredeclaredId = True
Attribute VB_Exposed = False
Attribute VB_TemplateDerived = False
Attribute VB_Customizable = False
Option Explicit

Private Sub ButtonDraw_1_Click()
    Placements.RunPlacements lPlace_1.Caption, "Placement_1"
End Sub

Private Sub ButtonDraw_2_Click()
    Placements.RunPlacements lPlace_2.Caption, "Placement_2"
End Sub

Private Sub ButtonDraw_3_Click()
    Placements.RunPlacements lPlace_3.Caption, "Placement_3"
End Sub

'Private Sub cmbPlace_Click()
'Do
'    If cbPlYes_1.Value = True Then
'        Placements.RunPlacements lPlace_1.Caption, "Placement_1"
'    End If
'    If cbPlYes_2.Value = True Then
'        Placements.RunPlacements lPlace_2.Caption, "Placement_2"
'    End If
'    If cbPlYes_3.Value = True Then
'        Placements.RunPlacements lPlace_3.Caption, "Placement_3"
'    End If
'Loop While cbCycle.Value = True
'End Sub

Attribute VB_Name = "ufSpanProfiles"
Attribute VB_Base = "0{C4BEBED1-98E6-4B2D-BBBC-F83D1020DA34}{274910B5-EACF-446B-B3C7-7B5233EB3C16}"
Attribute VB_GlobalNameSpace = False
Attribute VB_Creatable = False
Attribute VB_PredeclaredId = True
Attribute VB_Exposed = False
Attribute VB_TemplateDerived = False
Attribute VB_Customizable = False
Option Explicit

Private Sub lbSpanProfiles_Change()
    Profiles.RotateView
End Sub
