Attribute VB_Name = "Module1"
Option Explicit

Sub Main()
    UserForm1.Show vbModeless
End Sub

Attribute VB_Name = "UserForm1"
Attribute VB_Base = "0{F2B48BB3-E84A-441F-95B9-D6B6A8C6B144}{9E98FE32-0539-432F-9516-DC96E26ED00B}"
Attribute VB_GlobalNameSpace = False
Attribute VB_Creatable = False
Attribute VB_PredeclaredId = True
Attribute VB_Exposed = False
Attribute VB_TemplateDerived = False
Attribute VB_Customizable = False
Option Explicit

Private Sub CommandButton_cut_Click()
ClipFence
End Sub

Private Sub UserForm_Initialize()
    IniLevels
End Sub
Private Sub IniLevels()
    Dim myLevel As Level
        UserForm1.ComboBox_Levels.Clear
            For Each myLevel In ActiveDesignFile.Levels
                UserForm1.ComboBox_Levels.AddItem myLevel.Name
            Next
End Sub

Private Sub ClipFence()
    Dim fnc As Fence
    Dim saveClip As Boolean
    Dim saveOverlap As Boolean
    Dim saveVoid As Boolean
    Dim ee As ElementEnumerator
    Dim myView As View
    
    Dim myEnum As ElementEnumerator
    Dim mFilter As New ElementScanCriteria
    Dim i As Long
    
    Dim myFences() As Element
    
    mFilter.ExcludeAllLevels
    mFilter.ExcludeAllTypes
    
    mFilter.IncludeLevel ActiveDesignFile.Levels(UserForm1.ComboBox_Levels.Text)
    mFilter.IncludeType msdElementTypeShape
    mFilter.IncludeType msdElementTypeComplexShape
    mFilter.IncludeType msdElementTypeCellHeader
    
    Set myEnum = ActiveModelReference.Scan(mFilter)
    
    myFences = myEnum.BuildArrayFromContents
    
    Set myView = ActiveDesignFile.Views(1)
    Set fnc = ActiveDesignFile.Fence
    
    With ActiveSettings
        
        saveClip = .FenceClip
        .FenceClip = True
        saveOverlap = .FenceOverlap
        .FenceOverlap = False
        saveVoid = .FenceVoid
        .FenceVoid = False
    End With
    
    ActiveModelReference.Levels(ComboBox_Levels.Text).IsDisplayed = False
    
    For i = 0 To UBound(myFences)
        fnc.DefineFromElement myView, myFences(i)
        If Not fnc.IsDefined Then
            ShowError "The fence is not defined"
            Exit Sub
        End If
        Set ee = fnc.GetContents(False)
        While ee.MoveNext
            ActiveModelReference.RemoveElement ee.Current
            ee.Current.Redraw
        Wend
    Next i
    
    fnc.Undefine
    ActiveModelReference.Levels(ComboBox_Levels.Text).IsDisplayed = True
    
    With ActiveSettings
            .FenceClip = saveClip
            .FenceOverlap = saveOverlap
            .FenceVoid = saveVoid
        End With
    
End Sub
