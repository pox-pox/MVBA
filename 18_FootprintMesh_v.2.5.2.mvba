Attribute VB_Name = "Module1"
Sub Main()
    UserForm.Show vbModeless
        
'    ReDim Preserve myShape(UBound(myShape) - 1)
'    Set shape1(0) = myShape(UBound(myShape))
'    ReDim Preserve myShape(UBound(myShape) - 1)
'    Set union = GetRegionUnion(myShape, shape1, Nothing, msdFillModeNotFilled)
'    While union.MoveNext
'        ActiveModelReference.AddElement union.Current
'        union.Current.Redraw
'    Wend
End Sub

Attribute VB_Name = "UserForm"
Attribute VB_Base = "0{F4A0ED39-38E5-459A-89F4-19DF92DA603F}{BB8D8539-AE7D-401F-BBD8-AD903E6E5D13}"
Attribute VB_GlobalNameSpace = False
Attribute VB_Creatable = False
Attribute VB_PredeclaredId = True
Attribute VB_Exposed = False
Attribute VB_TemplateDerived = False
Attribute VB_Customizable = False
Private Sub IniLevels(mComboBox As ComboBox)
    Dim myLevel As Level
    mComboBox.Clear
        For Each myLevel In ActiveDesignFile.Levels
            mComboBox.AddItem myLevel.Name
        Next
End Sub

Function getEnumeratorCount(oEnumerator As ElementEnumerator) As Long
    Dim count As Long
    With oEnumerator
        .Reset
        Do While .MoveNext
            count = count + 1
        Loop
        .Reset
    End With
    getEnumeratorCount = count
End Function


Private Sub FootPrint()

Dim MyEnum As ElementEnumerator
    Dim sEnum As ElementEnumerator
    Dim myFilter As New ElementScanCriteria
    Dim sFilter As New ElementScanCriteria
    Dim point As Point3d
    Dim MyShape() As Element
    Dim mMesh() As Element
    Dim drMesh As Variant
    ReDim MyShape(0)
    Dim shape1() As Element
    ReDim shape1(0)
    Dim union As ElementEnumerator
    Dim bool As Boolean
    Dim i As Long
    Dim s As Double ' Площадь Shape
    Dim m As Long ' Количество Mesh
    Dim sh As Long ' Количество Shape
    Dim mMSG As VbMsgBoxResult
    
    myFilter.ExcludeAllTypes
    myFilter.ExcludeAllLevels
    
    myFilter.IncludeType msdElementTypeMeshHeader
    myFilter.IncludeLevel ActiveModelReference.Levels(ComboBox_Mesh_level.Text)
    
    Set MyEnum = ActiveModelReference.Scan(myFilter)
    m = getEnumeratorCount(MyEnum)
    mMesh = MyEnum.BuildArrayFromContents

    MsgResp = MsgBox("Найдено: " & m & " Mesh" & vbCr & "Сформировать FootPrint?", vbYesNo)
        Select Case MsgResp
            Case VbMsgBoxResult.vbYes
                While MyEnum.MoveNext
                    ActiveModelReference.SelectElement MyEnum.Current
                    CadInputQueue.SendCommand "DROP ELEMENT"
                    CadInputQueue.SendDataPoint point, 1
                    CommandState.StartDefaultCommand
                    
                    sFilter.ExcludeAllTypes
                    sFilter.ExcludeAllLevels
                    sFilter.IncludeOnlyNew
                    sFilter.IncludeType msdElementTypeShape
                    sFilter.IncludeLevel ActiveModelReference.Levels(ComboBox_Mesh_level.Text)
                    
                    Set sEnum = ActiveModelReference.Scan(sFilter)
                    While sEnum.MoveNext
                        ActiveModelReference.RemoveElement sEnum.Current
                        sEnum.Current.Redraw
                        Set MyShape(UBound(MyShape)) = sEnum.Current.AsShapeElement
                        MyShape(UBound(MyShape)).Transform Transform3dFromMatrix3dPoint3d(Matrix3dFromScaleFactors(1, 1, 0), Point3dFromXYZ(0, 0, 0))
                        ReDim Preserve MyShape(UBound(MyShape) + 1)
                    Wend
                        ReDim Preserve MyShape(UBound(MyShape) - 1)
                        Set shape1(0) = MyShape(0)
 '                       Set union = GetRegionUnion(shape1, shape1, Nothing, msdFillModeNotFilled)
'                            For i = 0 To UBound(MyShape)
'                                Set shape1(0) = MyShape(i)
'                                Set union = GetRegionUnion(union.BuildArrayFromContents, shape1, Nothing, msdFillModeNotFilled)
'                            Next i
                        Set union = GetRegionUnion(MyShape, shape1, Nothing, msdFillModeNotFilled)
                        While union.MoveNext
                            union.Current.Level = ActiveModelReference.Levels.Find(ComboBox_Shape_Level.Text)
                            ActiveModelReference.AddElement union.Current
                            union.Current.Redraw
                            sh = sh + 1
                        Wend
                    Erase MyShape
                    ReDim Preserve MyShape(0)
                Wend
                For Each drMesh In mMesh
                    ActiveModelReference.AddElement drMesh
                    drMesh.Redraw
                Next
                MsgBox "Сформировано: " & sh & " Shape"
            Case VbMsgBoxResult.vbNo
        Exit Sub
    End Select

    
'    m = getEnumeratorCount(MyEnum)
'    MsgResp = MsgBox("Найдено: " & m & " Mesh" & vbCr & "Сформировать FootPrint?", vbYesNo)
'    Select Case MsgResp
'        Case VbMsgBoxResult.vbYes
'            CadInputQueue.SendCommand "DROP ELEMENT"
'            CadInputQueue.SendDataPoint point, 1
'            CommandState.StartDefaultCommand
'
'            sFilter.ExcludeAllTypes
'            sFilter.IncludeOnlyNew
'            sFilter.IncludeType msdElementTypeShape
'            'sFilter.IncludeOnlyGraphicGroup
'            Set sEnum = ActiveModelReference.Scan(sFilter)
'            c = getEnumeratorCount(sEnum)
'                While sEnum.MoveNext
'                    If sEnum.Current.GraphicGroup > 0 Then
'                        sEnum.Current.Transform Transform3dFromMatrix3dPoint3d(Matrix3dFromScaleFactors(1, 1, 0), Point3dFromXYZ(0, 0, 0))
'                        k = k + 1
'                        Select Case sEnum.Current.Type
'                            Case msdElementTypeShape
'                            On Error Resume Next
'                            s = sEnum.Current.AsShapeElement.Area
'                            If Err.Number = 0 Then
'                                If s > 0 Then
'                                    If bool = False Then
'                                        Set shape1(0) = sEnum.Current
'                                        ActiveModelReference.RemoveElement sEnum.Current
'                                        sEnum.Current.Redraw
'                                        bool = True
'                                        GG = shape1(0).GraphicGroup
'                                        Set union = GetRegionUnion(shape1, shape1, Nothing, msdFillModeNotFilled)
'                                    ElseIf bool = True Then
'                                        If sEnum.Current.AsShapeElement.GraphicGroup = GG And k < c Then
'                                            Set shape1(0) = sEnum.Current
'                                            Set union = GetRegionUnion(union.BuildArrayFromContents, shape1, Nothing, msdFillModeNotFilled)
'
''                                            Set MyShape(UBound(MyShape)) = sEnum.Current
'                                            ActiveModelReference.RemoveElement sEnum.Current
'                                            sEnum.Current.Redraw
''                                            ReDim Preserve MyShape(UBound(MyShape) + 1)
'                                        Else
''                                            ReDim Preserve MyShape(UBound(MyShape) - 1)
''                                            ActiveModelReference.AddElement shape1(0)
''                                            shape1(0).Redraw
''                                            Set union = GetRegionUnion(MyShape, shape1, Nothing, msdFillModeNotFilled)
'                                                While union.MoveNext
'                                                    union.Current.Level = ActiveModelReference.Levels.Find(ComboBox_Shape_Level.Text)
'                                                    ActiveModelReference.AddElement union.Current
'                                                    union.Current.Redraw
'                                                    sh = sh + 1
'                                                Wend
'                                            Set shape1(0) = sEnum.Current
'                                            ActiveModelReference.RemoveElement sEnum.Current
'                                            sEnum.Current.Redraw
'                                            ReDim Preserve MyShape(0)
'                                            Erase MyShape
'                                        End If
'                                    End If
'                                End If
'                            Else
'                                ActiveModelReference.RemoveElement sEnum.Current
'                                sEnum.Current.Redraw
'                            End If
'                            Err.Clear
'                        End Select
'                    End If
'                Wend
'            MsgBox "Сформировано: " & sh & " Shape"
'            For Each drMesh In mMesh
'                ActiveModelReference.AddElement drMesh
'                drMesh.Redraw
'            Next
'        Case VbMsgBoxResult.vbNo
'        Exit Sub
'    End Select
End Sub

Private Sub CommandButton_FootPrint_Click()
    FootPrint
End Sub

Private Sub UserForm_Initialize()
    IniLevels ComboBox_Mesh_level
    IniLevels ComboBox_Shape_Level
End Sub

Private Function ComplexShapeToShape(CShape As Element) As ShapeElement
    Dim MyEnum As ElementEnumerator
    Dim MyShape As ShapeElement
    Dim Verteces() As Point3d
    Dim i As Integer
    ReDim Verteces(0)
    If CShape.IsComplexShapeElement Then
        Set MyEnum = CShape.AsComplexShapeElement.GetSubElements
            While MyEnum.MoveNext
                For i = 0 To UBound(MyEnum.Current.AsVertexList.GetVertices)
                    Verteces(UBound(Verteces)) = MyEnum.Current.AsLineElement.Vertex(i + 1)
                    ReDim Preserve Verteces(UBound(Verteces) + 1)
                Next i
                ReDim Preserve Verteces(UBound(Verteces) - 1)
            Wend
        Set MyShape = CreateShapeElement1(CShape, Verteces, msdFillModeNotFilled)
        MyShape.IsSnappable = True
        Set ComplexShapeToShape = MyShape
    ElseIf CShape.IsShapeElement Then
        Set ComplexShapeToShape = CShape.AsShapeElement
    End If
End Function
