Attribute VB_Name = "Module1"
Option Explicit
Public myRegion As LineElement
Sub Main()
    Myform.Show vbModeless
End Sub

Attribute VB_Name = "Myform"
Attribute VB_Base = "0{43396A18-F4CC-4682-87AC-944F07DDE4DF}{A8625497-8B1B-4503-A50B-246A6EF32CA7}"
Attribute VB_GlobalNameSpace = False
Attribute VB_Creatable = False
Attribute VB_PredeclaredId = True
Attribute VB_Exposed = False
Attribute VB_TemplateDerived = False
Attribute VB_Customizable = False
Option Explicit
Sub btCreateFn_Click()
If cbRegion.Value = True Or cbCreateRegion.Value = True Then
    CommandState.StartPrimitive New PCE_Create_region
Else: InputFence CDbl(tbOffset.Text), cmbCell.Text
End If

End Sub
Function ins(myElement As Element, myPoint As Point3d) As Boolean
    Dim iPoint() As Point3d
    Dim myLine As LineElement
    Dim finishP As Point3d
    finishP.Y = myPoint.Y + 50000000
    Set myLine = CreateLineElement2(Nothing, myPoint, finishP)
            iPoint = myElement.AsIntersectableElement.GetIntersectionPointsOnIntersector(myLine, Matrix3dIdentity)
            If (UBound(iPoint) + 1) Mod 2 > 0 Then ins = True Else ins = False
End Function
'Function NumCross(Pt3d() As Point3d, myPt As Point3d) As Integer
    'ReDim Preserve Pt3d(UBound(Pt3d))
    'Dim stX, stY, fnX, fnY As Double
    'Dim Num As Integer
    'Dim b As Double
    'Dim i As Double
    'For i = 0 To (UBound(Pt3d))
    '   If i <> UBound(Pt3d) Then                ' Перенос начала системы координат в проверяемую точку
      '      stX = Pt3d(i).X - myPt.X
      '      stY = Pt3d(i).Y - myPt.Y
       '     fnX = Pt3d(i + 1).X - myPt.X
       '     fnY = Pt3d(i + 1).Y - myPt.Y
       'ElseIf i = UBound(Pt3d) Then
       '     stX = Pt3d(i).X - myPt.X
       '     stY = Pt3d(i).Y - myPt.Y
        '    fnX = Pt3d(0).X - myPt.X
       '     fnY = Pt3d(0).Y - myPt.Y
       'End If
       'If stX <> fnX Then                                           ' вычисление коэффециента b
          '  b = (stY - ((fnY - stY) / (fnX - stX)) * stX)
      ' ElseIf stX = fnX Then
       '     b = 0
       'End If
      ' If (stX >= 0 And fnX < 0 And b > 0) Or (fnX > 0 And stX < 0 And b > 0) Then Num = Num + 1   ' Проверка на пересечение отрезка с прямой x=0 и y>0
   ' Next
       ' NumCross = Num
'End Function

Function CreatVegArray(Fence() As Point3d, offs As Double) As Variant
ReDim Preserve Fence(UBound(Fence))
Dim Xmax As Double
Dim Xmin As Double
Dim Ymax As Double
Dim Ymin As Double
Dim DX As Double
Dim DY As Double
Dim k As Double
Dim l As Double
Dim R As Double
Dim i As Long
Dim j As Double
Dim q As Double
q = 0

Dim ptVeg() As Point3d
Xmax = Fence(0).X
Ymax = Fence(0).Y
Xmin = Fence(0).X
Ymin = Fence(0).Y

For i = 0 To (UBound(Fence))
    If Fence(i).X > Xmax Then Xmax = Fence(i).X
    If Fence(i).Y > Ymax Then Ymax = Fence(i).Y
    If Fence(i).X < Xmin Then Xmin = Fence(i).X
    If Fence(i).Y < Ymin Then Ymin = Fence(i).Y
Next i
DX = Xmax - Xmin
DY = Ymax - Ymin
k = DX \ offs
l = (DY \ offs) * 2
ReDim Preserve ptVeg(((k + 1) * (l + 1)) - 1)
    For i = 0 To l
        For j = 0 To k
               If (i Mod 2) > 0 Then
                    R = Int((Rnd * offs * 0.5) - offs * 0.25)
                    If cbLes.Value = False Then R = 0
                    ptVeg(q).X = Xmin + offs * j + offs / 2 + R + 0.1
               ElseIf ((i Mod 2) = 0) Or i = 0 Then
                    ptVeg(q).X = Xmin + offs * j + R + 0.1
               End If
               R = Int((Rnd * offs * 0.4) - offs * 0.2)
               If cbLes.Value = False Then R = 0
               ptVeg(q).Y = Ymin + (offs / 2) * i + R
            q = q + 1
        Next j
    Next i
CreatVegArray = ptVeg
End Function
Sub InputFence(offset As Double, cellTxt As String)
    Dim MyEnumCSh As ElementEnumerator
    Dim myCIQ As CadInputQueue
    Dim myCIM As CadInputMessage
    Dim VertFence() As Point3d
    Dim Fence As LineElement
    ReDim VertFence(0)
    Set myCIQ = CadInputQueue
    Dim Pt As Point3d
    Dim с As Integer                'Количество пересечений
    Dim vegInsFence() As Point3d
    ReDim vegInsFence(0)
    Dim Fill() As Point3d
    Dim j As Long
    Dim i As Long
    Dim f As Double ' Количество элементов по экстентам контура
    Dim cell As CellElement
    Dim myShape As ShapeElement 'Контур внутри которого проводится заливка знаками (для поиска пересечений)
    Dim myLine As LineElement
    Dim MyCShape1 As ComplexShapeElement
    Dim CShapeEnum As ElementEnumerator
    Dim PsevdoShape As LineElement
    'f = UBound(CreatVegArray(VertFence(), offset))
    'ReDim Preserve Fill(f)
    'Fill = CreatVegArray(VertFence(), offset)
    If cbSelect.Value = True Then
        ReDim Preserve VertFence(UBound(GetShape) - 1)
        VertFence = GetShape
        f = UBound(CreatVegArray(VertFence(), offset))
        ReDim Preserve Fill(f)
    Fill = CreatVegArray(VertFence(), offset)
    ElseIf cbRegion.Value = True Then
        'CommandState.StartPrimitive New PCE_Create_region
        VertFence = myRegion.GetVertices
        ReDim Preserve VertFence(UBound(VertFence) - 1)
        f = UBound(CreatVegArray(VertFence(), offset))
        ReDim Preserve Fill(f)
        Fill = CreatVegArray(VertFence(), offset)

    ElseIf cbSelect.Value = False And cbRegion.Value = False Then
          Set myCIM = myCIQ.GetInput
        Select Case myCIM.InputType
                Case msdCadInputTypeDataPoint
                    VertFence(UBound(VertFence)) = myCIM.Point
                    Debug.Print "vert =" & (UBound(VertFence) + 1)
                    Debug.Print "X =" & VertFence(UBound(VertFence)).X
                    Debug.Print "Y =" & VertFence(UBound(VertFence)).Y
                    ReDim Preserve VertFence(UBound(VertFence) + 1)
                Case msdCadInputTypeReset
                    Err.Raise -12345
                    Exit Sub
        End Select
        CadInputQueue.SendCommand "PLACE FENCE SHAPE"
        CadInputQueue.SendDataPoint VertFence(UBound(VertFence) - 1)
    Do While True
        Set myCIM = myCIQ.GetInput
            Select Case myCIM.InputType
                Case msdCadInputTypeDataPoint
                    VertFence(UBound(VertFence)) = myCIM.Point
                    Debug.Print "vert =" & (UBound(VertFence) + 1)
                    Debug.Print "X =" & VertFence(UBound(VertFence)).X
                    Debug.Print "Y =" & VertFence(UBound(VertFence)).Y
                    ReDim Preserve VertFence(UBound(VertFence) + 1)
                Case msdCadInputTypeReset
                    Exit Do
            End Select
    CadInputQueue.SendDataPoint VertFence(UBound(VertFence) - 1)
    Loop
    ReDim Preserve VertFence(UBound(VertFence) - 1)
        f = UBound(CreatVegArray(VertFence(), offset))
        ReDim Preserve Fill(f)
        Fill = CreatVegArray(VertFence(), offset)
    End If
    
    If cbSelect.Value = False Or cbRegion.Value = True Then
    Set myShape = CreateShapeElement1(Nothing, VertFence, msdFillModeNotFilled)
    
    For i = 0 To f
        'If NumCross(VertFence(), Fill(i)) Mod 2 > 0 Then
        If ins(myShape, Fill(i)) Then
        vegInsFence(j) = Fill(i)
        j = j + 1
        ReDim Preserve vegInsFence(j)
        End If
    Next i
    ElseIf cbSelect.Value = True Then
    Set MyEnumCSh = ActiveModelReference.GetSelectedElements
    While MyEnumCSh.MoveNext
    For i = 0 To f
    If ins(MyEnumCSh.Current, Fill(i)) Then
        vegInsFence(j) = Fill(i)
        j = j + 1
        ReDim Preserve vegInsFence(j)
        End If
    Next i
    Wend
    End If
    
    If cbSelect.Value = True Then
    Set MyEnumCSh = ActiveModelReference.GetSelectedElements
    While MyEnumCSh.MoveNext
        Select Case MyEnumCSh.Current.Type
            Case msdElementTypeShape
                    Set myShape = CreateShapeElement1(Nothing, VertFence, msdFillModeNotFilled)
                For i = 0 To (j - 1)
                    Set cell = CreateCellElement3(cellTxt, vegInsFence(i), True)
                    If IntersectCell(cell, myShape) = False Then
                        ActiveModelReference.AddElement cell
                        cell.Redraw
                        Else: Debug.Print "del"
                    End If
                 Next i
            Case msdElementTypeComplexShape
            Set MyCShape1 = MyEnumCSh.Current
            'Set CShapeEnum = MyCShape1.GetSubElements
               ' While CShapeEnum.MoveNext
                  '  Set MyLine = CShapeEnum.Current
                        For i = 0 To (j - 1)
                            Set cell = CreateCellElement3(cellTxt, vegInsFence(i), True)
                            If IntersectCell(cell, MyCShape1) = False Then
                                ActiveModelReference.AddElement cell
                                cell.Redraw
                                'Else: Debug.Print "del"
                            End If
                        Next i
               ' Wend
        End Select
    Wend
    ElseIf cbSelect.Value = False Then
    Set myShape = CreateShapeElement1(Nothing, VertFence, msdFillModeNotFilled)
                For i = 0 To (j - 1)
                    Set cell = CreateCellElement3(cellTxt, vegInsFence(i), True)
                    If IntersectCell(cell, myShape) = False Then
                        cell.Level = ActiveDesignFile.Levels.Find(ActiveSettings.Level.Name)
                        ActiveModelReference.AddElement cell
                        cell.Redraw
                        Else: Debug.Print "del"
                    End If
                 Next i
    End If
End Sub
Function IntersectCell(myCell As CellElement, myElement As Element) As Boolean 'Проверка на пересечение
    Dim myEnum As ElementEnumerator
    Dim iPoint() As Point3d
    Dim Inter As Boolean
    Inter = False
    Set myEnum = myCell.GetSubElements
        While myEnum.MoveNext
            If myEnum.Current.Type = msdElementTypeLineString Or myEnum.Current.Type = msdElementTypeShape Or myEnum.Current.Type = msdElementTypeEllipse Then
                iPoint = myEnum.Current.AsIntersectableElement.GetIntersectionPointsOnIntersector(myElement, Matrix3dIdentity)
                If UBound(iPoint) >= 0 Then Inter = True
            End If
        Wend
    IntersectCell = Inter
End Function
Function GetShape() As Variant ' Возвращает массив точек выделенного Shape без последнего вертекса
    Dim MyEnumCSh As ElementEnumerator
    Dim myShape As ShapeElement
    Dim myLine As LineElement
    Dim MyCShape1 As ComplexShapeElement
    Dim CShapeEnum As ElementEnumerator
    Dim Points() As Point3d
    ReDim Points(0)
    Dim V As Double
    Dim i As Double
    Dim j As Double
    Dim k As Integer
    j = 0
    Set MyEnumCSh = ActiveModelReference.GetSelectedElements
    While MyEnumCSh.MoveNext
        Select Case MyEnumCSh.Current.Type
            Case msdElementTypeShape
                Set myShape = MyEnumCSh.Current
                Debug.Print "shape"
    V = myShape.VerticesCount
    ReDim Preserve Points(V - 1)
    Points = myShape.GetVertices
    ReDim Preserve Points(V - 2)
          Case msdElementTypeComplexShape
                Set MyCShape1 = MyEnumCSh.Current
                Set CShapeEnum = MyCShape1.GetSubElements
                    While CShapeEnum.MoveNext
                        Set myLine = CShapeEnum.Current
                        V = myLine.VerticesCount
                        Debug.Print "V=" & V
                            If j = 0 Then k = -1 Else k = 0
                        ReDim Preserve Points(UBound(Points) + V + k - 1)
                        For i = 1 To (V - 1)
                        Points(j) = myLine.Vertex(i)
                        j = j + 1
                        Next i
                    Wend
                End Select
    Wend
    GetShape = Points
End Function

Private Sub cbCreateRegion_Change()
    If cbCreateRegion.Value = True Then
        tbTolerance.Enabled = True
        lTolerance.Enabled = True
    Else: tbTolerance.Enabled = False
        lTolerance.Enabled = False
    End If
End Sub


Private Sub cbRegion_Change()
    If cbRegion.Value = True Then
        tbTolerance.Enabled = True
        lTolerance.Enabled = True
    Else: tbTolerance.Enabled = False
        lTolerance.Enabled = False
    End If
End Sub



Private Sub cmbCell_Click()
    UserForm_Initialize
End Sub

Private Sub UserForm_Initialize()
    Dim MyCellEnum As CellInformationEnumerator
    Dim myCell As CellInformation
    If IsCellLibraryAttached Then
        Set MyCellEnum = Application.GetCellInformationEnumerator(False, False)
        While MyCellEnum.MoveNext
            Set myCell = MyCellEnum.Current
            cmbCell.AddItem myCell.Name
        Wend
        Else: MsgBox "Библиотека Cell не подключена", vbOKOnly
    End If
End Sub

Attribute VB_Name = "PCE_Create_region"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Implements IPrimitiveCommandEvents
Private aCandidates() As Element
Private oElement As Element
Private Sub IPrimitiveCommandEvents_Cleanup()

End Sub

Private Sub IPrimitiveCommandEvents_DataPoint(Point As Point3d, ByVal View As View)
    Dim myFilter As New ElementScanCriteria
    Dim myEnum As ElementEnumerator
    Dim shEnum As ElementEnumerator
    Dim myReg As ComplexElement
    Dim myShape As ShapeElement
    Dim i As Long
    
   
    myFilter.ExcludeAllTypes
    myFilter.IncludeType msdElementTypeLineString
    myFilter.IncludeType msdElementTypeShape
    myFilter.IncludeType msdElementTypeComplexShape
    myFilter.IncludeType msdElementTypeLine
    
   
    
    Set myEnum = ActiveModelReference.Scan(myFilter)
            While myEnum.MoveNext
            If myEnum.Current.Level.IsDisplayedInView(ActiveDesignFile.Views.Item(1)) = True Then
                Set aCandidates(i) = myEnum.Current
                i = i + 1
                ReDim Preserve aCandidates(i)
            End If
        Wend
    ReDim Preserve aCandidates(i - 1)

    Set oElement = GetFloodBoundary(aCandidates, Nothing, Point, , False, CDbl(Myform.tbTolerance.Text), msdFillModeFilled)
    'ActiveModelReference.AddElement oElement
    'oElement.Redraw
    If oElement Is Nothing Then MsgBox "Регион не построен", vbOKOnly
    Set myReg = oElement
    Set shEnum = myReg.GetSubElements
        While shEnum.MoveNext
            Set myRegion = shEnum.Current
        Wend
    If Myform.cbRegion.Value = True Then
        Myform.InputFence CDbl(Myform.tbOffset.Text), Myform.cmbCell.Text
        CommandState.StartDefaultCommand
    ElseIf Myform.cbCreateRegion.Value = True Then
        Set myShape = CreateShapeElement1(Nothing, myRegion.GetVertices, msdFillModeNotFilled)
        ActiveModelReference.AddElement myShape
        myShape.Redraw
        CommandState.StartDefaultCommand
    End If
    

End Sub

Private Sub IPrimitiveCommandEvents_Dynamics(Point As Point3d, ByVal View As View, ByVal DrawMode As MsdDrawingMode)

End Sub

Private Sub IPrimitiveCommandEvents_Keyin(ByVal Keyin As String)

End Sub

Private Sub IPrimitiveCommandEvents_Reset()
    'Myform.InputFence CDbl(Myform.tbOffset.Text), Myform.cmbCell.Text
End Sub

Private Sub IPrimitiveCommandEvents_Start()
    ReDim aCandidates(0)
End Sub
