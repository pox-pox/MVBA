Attribute VB_Name = "Module1"
Option Explicit

Private Type BrowseInfo
    hWndOwner As Long
    pidlRoot As Long
    sDisplayName As String
    sTitle As String
    ulFlags As Long
    lpfn As Long
    lParam As Long
    iImage As Long
End Type

Private Declare Function SHBrowseForFolder Lib "shell32.dll" (bBrowse As BrowseInfo) As Long
Private Declare Function SHGetPathFromIDList Lib "shell32.dll" (ByVal Item As Long, ByVal sDir As String) As Long

Private Const Bif_ReturnOnlyFSDirs = 1
Private Const Bif_DontGoBelowDomain = 2
Private Const Bif_EditBox = 16
Private Const Bif_NewDialogStyle = 64
Private Const Bif_UseNewui = 80
Private Const Bif_BrowseForComputer = 4096
Private Const Bif_BrowseForPrinter = 8192
Private Const Bif_BrowseIncludeFiles = 16384

Declare Function mdlDialog_fileOpen Lib "stdmdlbltin.dll" (ByVal _
    fileName As String, ByVal rFileH As Long, ByVal _
    resourceId As Long, ByVal suggestedFileName As String, _
    ByVal filterString As String, ByVal defaultDirectory As String, _
    ByVal titleString As String) As Long
Public dgntmpName As String
Public PathDGN As String
Public CuttingFilesPath() As String

Public Sub Select_temp()
    Dim strFName As String
    Dim lngfhandle As Long
    Dim lngrid As Long
    Dim retVal As Long
    strFName = Space(255)
    retVal = mdlDialog_fileOpen(strFName, lngfhandle, lngrid, "", "*.dgn", _
                                    ActiveDesignFile.Path, "Выбрать шаблон DGN")
    dgntmpName = Left(strFName, InStr(1, strFName, Chr(0)) - 1)
    UserForm1.Label_TargetFolder.Caption = Left(dgntmpName, InStrRev(dgntmpName, "\"))
End Sub

Public Sub SelectFolder()
'    Dim myshell As New Shell32.Shell
'    Dim myFolder As She1132.Folder3
''    Dim myfolder2 As She1132.Folder3
''    Dim myItem As Shell32.FolderItem
'    Set myFolder = myshell.BrowseForFolder(O, “Browse”, 0)
'    MsgBox myFolder.Se1f.Path
    
    Dim MyBI As BrowseInfo
    Dim FList As Long
    Dim DirName As String
    Dim SelFolder As Long
    DirName = Space(255)
    
    MyBI.sTitle = "Выбрать результирующую папку:"
    MyBI.sDisplayName = Space(255)
    MyBI.ulFlags = Bif_ReturnOnlyFSDirs
    FList = SHBrowseForFolder(MyBI)
    SelFolder = SHGetPathFromIDList(FList, DirName)
    DirName = Left(DirName, InStr(1, DirName, Chr(0)) - 1)
    
        If DirName <> " " Then
            PathDGN = DirName
        Else
            PathDGN = ""
        End If
    'PathDGN = myFolder.Se1f.Path
    UserForm1.TextBox_FromFolder.Text = PathDGN
    PopulateFileList
End Sub

Sub PopulateFileList()

    UserForm1.ListBox_CuttingFiles.Clear
    Dim myFolder As Folder
    Dim myFSO As New FileSystemObject
    Dim chkSubFolders As Boolean
    
    
    If UserForm1.TextBox_FromFolder.Text <> "" Then
        Set myFolder = myFSO.GetFolder(UserForm1.TextBox_FromFolder.Text)
        FilesInFolder myFolder, "dgn", chkSubFolders, UserForm1.ListBox_CuttingFiles
    End If
    UserForm1.lblFiles.Caption = "В папке найдено - " & UserForm1.ListBox_CuttingFiles.ListCount & " DGN файлов."
    
End Sub

Sub FilesInFolder(FolderIn As Folder, FileExtension As String, Includesubs As Boolean, ListToPopulate As ListBox)
    Dim myFile As File

    For Each myFile In FolderIn.Files
        Select Case UCase(FileExtension)
            Case UCase(Right(myFile.Name, 3))
                ListToPopulate.AddItem Right(myFile.Path, Len(myFile.Path) - InStrRev(myFile.Path, "\"))
        End Select
    Next

End Sub

Sub ReadFilesPath()
    Dim i As Long
    ReDim CuttingFilesPath(0)
    For i = 1 To UserForm1.ListBox_CuttingFiles.ListCount
        If UserForm1.ListBox_CuttingFiles.Selected(i - 1) = True Then
            CuttingFilesPath(UBound(CuttingFilesPath)) = UserForm1.ListBox_CuttingFiles.List(i - 1)
            ReDim Preserve CuttingFilesPath(UBound(CuttingFilesPath) + 1)
        End If
    Next i
    ReDim Preserve CuttingFilesPath(UBound(CuttingFilesPath) - 1)
End Sub

Public Sub Copy_dgn()
    Dim PathDGN As String
    
    PathDGN = Left(dgntmpName, InStr(1, dgntmpName, ".dgn") - 1)
    Debug.Print PathDGN
    CopyDesignFile dgntmpName, PathDGN & "_copy.dgn", True
    
End Sub

Sub Main()
    UserForm1.Show vbModeless
End Sub

Attribute VB_Name = "UserForm1"
Attribute VB_Base = "0{E9299DA7-DF3D-4FB6-8AF4-4F9068D7B6F6}{2FCB2AD1-CC90-459E-AFB1-1BB558F2E5ED}"
Attribute VB_GlobalNameSpace = False
Attribute VB_Creatable = False
Attribute VB_PredeclaredId = True
Attribute VB_Exposed = False
Attribute VB_TemplateDerived = False
Attribute VB_Customizable = False
Option Explicit


Private Sub IniLevels()
    Dim myLevel As Level
        UserForm1.ComboBox_Levels.Clear
            For Each myLevel In ActiveDesignFile.Levels
                UserForm1.ComboBox_Levels.AddItem myLevel.Name
            Next
End Sub


Private Sub CommandButton_Analize_Click()
    AnalizeIntersect
    
End Sub

Private Sub CommandButton_copyDGN_Click()
    Copy_dgn
End Sub

Private Sub CommandButton_Select_tmp_Click()
    Module1.Select_temp
    Debug.Print dgntmpName
End Sub

Private Sub CommandButton_tarFolder_Click()
    Module1.SelectFolder
End Sub

Private Sub CommandButton1_Click()
   ' CutFence
    ReadFilesPath
    CopyFenceContents
End Sub

Private Sub UserForm_Initialize()
    IniLevels
End Sub

Sub Copy_element(curElement() As Element, suff As String)
    Dim df As DesignFile
    Dim oMDL As ModelReference
    Dim i As Long
    
    Dim cc As New CopyContext
    Dim myFileName As String
    
    myFileName = PathDGN & "/" & UserForm1.TextBox_targetFileName.Text & suff & ".dgn"
    
    CreateDesignFile "seed3d", myFileName, False
    Set df = OpenDesignFileForProgram(myFileName, False)
    Set oMDL = df.DefaultModelReference
    cc.LevelHandling = msdCopyContextLevelCopyAlways
    
    
     For i = 0 To UBound(curElement)
  '   On Error Resume Next
'        If curElement(i).Level.Name <> UserForm1.ComboBox_Levels.Text Then
            oMDL.CopyElement curElement(i), cc
  '      End If
        ActiveModelReference.RemoveElement curElement(i)
        curElement(i).Redraw
     Next i
     
    df.Save
    Set cc = Nothing
    df.RewriteLevels
    df.Save
End Sub


 Sub CopyFenceContents()
    Dim fnc As Fence
    Dim ee As ElementEnumerator
    Dim saveClip As Boolean
    Dim saveOverlap As Boolean
    Dim saveVoid As Boolean
    Dim i As Long
    
    Dim myElement As Element
    Dim myEnum As ElementEnumerator
    Dim mFilter As New ElementScanCriteria
    Dim myView As View
    Dim myElems() As Element
    Dim myFences() As Element
    Dim myFencesIN() As Element
    
    Dim j As Long
    
    Dim oFile As DesignFile
    Dim sFullFileName As String
    
    Dim df As DesignFile
    Dim oMDL As ModelReference
    Dim cc As New CopyContext
    Dim cutFilePath As String
    Dim f As Long
    
    mFilter.ExcludeAllLevels
    mFilter.ExcludeAllTypes
    
    mFilter.IncludeLevel ActiveDesignFile.Levels(UserForm1.ComboBox_Levels.Text)
    mFilter.IncludeType msdElementTypeShape
    mFilter.IncludeType msdElementTypeComplexShape
    
'    Set myFence = ActiveDesignFile.Fence
'    myFence.Undefine
    
    With ActiveSettings
        saveClip = .FenceClip
        .FenceClip = True
        saveOverlap = .FenceOverlap
        .FenceOverlap = False
        saveVoid = .FenceVoid
        .FenceVoid = False
    End With
    
    Set myEnum = ActiveModelReference.Scan(mFilter)
    
    myFences = myEnum.BuildArrayFromContents
    cc.LevelHandling = msdCopyContextLevelCopyAlways
    
    For f = 0 To UBound(CuttingFilesPath)
        cutFilePath = PathDGN & "\" & CuttingFilesPath(f)
        Set df = OpenDesignFileForProgram(cutFilePath, False)
        Set oMDL = df.DefaultModelReference
        Set fnc = df.Fence
        Set myView = df.Views(1)
        fnc.Undefine
            For j = 0 To UBound(myFences)
                oMDL.CopyElement myFences(j), cc
            Next j
        df.RewriteLevels
        df.Save
        mFilter.ExcludeAllLevels
    mFilter.ExcludeAllTypes
    
    mFilter.IncludeLevel df.Levels(UserForm1.ComboBox_Levels.Text)
    mFilter.IncludeType msdElementTypeShape
    mFilter.IncludeType msdElementTypeComplexShape
        Set myEnum = oMDL.Scan(mFilter)
        myFencesIN = myEnum.BuildArrayFromContents
            For j = 0 To UBound(myFencesIN)
                fnc.DefineFromElement myView, myFencesIN(j)
                If Not fnc.IsDefined Then
                    ShowError "The fence is not defined"
                    Exit Sub
                End If
                Set ee = fnc.GetContents(True)
                myElems = ee.BuildArrayFromContents
                Copy_element myElems, Format(CStr(j), UserForm1.TextBox_Razryd.Text)
          Next j
          df.Save
             Set cc = Nothing
    df.RewriteLevels
    df.Save
    Next f
    
'        While myEnum.MoveNext
'            Set myElement = myEnum.Current
'            Debug.Print myElement.Type
'            Set myView = ActiveDesignFile.Views(1)
'           ' On Error Resume Next
'            'Set fnc = ActiveDesignFile.Fence
'             fnc.DefineFromElement myView, myElement
'
'                If Not fnc.IsDefined Then
'                    ShowError "The fence is not defined"
'                    Exit Sub
'                End If
'                Set ee = fnc.GetContents(True)
'                myElems = ee.BuildArrayFromContents
'
'                Copy_element myElems, Format(CStr(i), UserForm1.TextBox_Razryd.Text)
''                     Do While ee.MoveNext
''                         Dim ele As Element
''                         '  ee.Current is returning a copy of the element
''                         '  because this program called GetContents with
''                         '  the CloneElements argument set to True.
''                         Set ele = ee.Current
''                         ele.Move Point3dFromXYZ(500, i, 0)
''                         ele.Rewrite
''                         ele.Redraw
''                    Loop
'                i = i + 1
'        Wend
        
        With ActiveSettings
            .FenceClip = saveClip
            .FenceOverlap = saveOverlap
            .FenceVoid = saveVoid
        End With
'       myFence.Undefine
 End Sub

Sub AnalizeIntersect()
    Dim myEnum As ElementEnumerator
    Dim myEnumMesh As ElementEnumerator
    Dim mFilter As New ElementScanCriteria
    Dim mFilterMesh As New ElementScanCriteria
    Dim myElems() As Element
    Dim myElemsMesh() As Element
    Dim InterPoint() As Point3d
    
    Dim i As Long
    Dim j As Long
    
    mFilter.ExcludeAllLevels
    mFilter.ExcludeAllTypes
    
    mFilterMesh.ExcludeAllTypes
    
    mFilterMesh.IncludeType msdElementTypeMeshHeader
    
    
    mFilter.IncludeLevel ActiveDesignFile.Levels(UserForm1.ComboBox_Levels.Text)
    mFilter.IncludeType msdElementTypeShape
    mFilter.IncludeType msdElementTypeComplexShape
    
    Set myEnum = ActiveModelReference.Scan(mFilter)
    Set myEnumMesh = ActiveModelReference.Scan(mFilterMesh)
    myElems = myEnum.BuildArrayFromContents
    myElemsMesh = myEnumMesh.BuildArrayFromContents
    
    For i = 0 To UBound(myElems)
        For j = 0 To UBound(myElemsMesh)
            InterPoint = myElems(i).AsIntersectableElement.GetIntersectionPoints(myElemsMesh(j), Matrix3dIdentity)
                If UBound(InterPoint) <> -1 Then
                    myElems(i).Color = 3
                    myElems(i).Redraw
                    myElems(i).Rewrite
                End If
        Next j
    Next i
    
    
    
End Sub
