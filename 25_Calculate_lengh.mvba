Attribute VB_Name = "Module1"
Sub Main()
    UserForm.Show vbModeless
End Sub

Attribute VB_Name = "UserForm"
Attribute VB_Base = "0{4AA59DD6-E9C1-4973-B873-8DAD7499E0B4}{E1883281-78D6-44AA-AAA1-1596A31415CB}"
Attribute VB_GlobalNameSpace = False
Attribute VB_Creatable = False
Attribute VB_PredeclaredId = True
Attribute VB_Exposed = False
Attribute VB_TemplateDerived = False
Attribute VB_Customizable = False
Private Sub InitializeLevel(myCombo As ComboBox)
    Dim myLevel As Level
        For Each myLevel In ActiveModelReference.Levels
            myCombo.AddItem myLevel.Name
        Next
End Sub
Private Sub CommandButton_Calculate_Click()
    CalculateLengh
End Sub
Private Sub UserForm_DblClick(ByVal Cancel As MSForms.ReturnBoolean)
        InitializeLevel UserForm.ComboBox_Level
End Sub
Private Sub UserForm_Initialize()
    InitializeLevel UserForm.ComboBox_Level
End Sub
Private Sub CalculateLengh()
    Dim myEnum As ElementEnumerator
    Dim ComplexString As ElementEnumerator
    Dim myFilter As New ElementScanCriteria
    Dim l As Double ' Длина
    Dim i As Long   ' Количество Linestring
    Dim j As Long   ' Количество ComplexChaine
    Dim k As Long   ' Количество Line

    myFilter.ExcludeAllTypes
    myFilter.ExcludeAllLevels
    
    myFilter.IncludeLevel ActiveDesignFile.Levels(UserForm.ComboBox_Level.Text)
    myFilter.IncludeType msdElementTypeLineString
    myFilter.IncludeType msdElementTypeLine
    myFilter.IncludeType msdElementTypeComplexString
    
    Set myEnum = ActiveModelReference.Scan(myFilter)
    
    While myEnum.MoveNext
        Select Case myEnum.Current.Type
            Case msdElementTypeLineString
                l = l + myEnum.Current.AsLineElement.Length
                i = i + 1
            Case msdElementTypeComplexString
                l = l + myEnum.Current.AsComplexStringElement.Length
                j = j + 1
            Case msdElementTypeLine
                l = l + myEnum.Current.AsLineElement.Length
                k = k + 1
        End Select
    Wend
    MsgBox "Длинна: " & FormatNumber(Round(l, 2), CInt(2), vbTrue, vbFalse, vbTrue) & " м" & vbCr & "LineString: " & i & vbCr & "ComplexChain: " & j & vbCr & "Line: " & k
End Sub
