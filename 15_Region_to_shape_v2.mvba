Attribute VB_Name = "Module1"
Sub Main()
    UserForm1.Show vbModeless
End Sub

Attribute VB_Name = "PCE_Create_region"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Implements IPrimitiveCommandEvents
Private aCandidates() As Element
Private oElement As Element
Private Sub IPrimitiveCommandEvents_Cleanup()

End Sub
Private Sub IPrimitiveCommandEvents_DataPoint(Point As Point3d, ByVal View As View)
    Dim myFilter As New ElementScanCriteria
    Dim MyEnum As ElementEnumerator
    Dim shEnum As ElementEnumerator
    Dim myReg As ComplexElement
    Dim MyShape As ShapeElement
    Dim myRegion As ShapeElement
    Dim i As Long
    Dim MyPoint As Point3d ' Точка задающая регион
    Dim Mhole As Boolean ' Делать дыры
    
    myFilter.ExcludeAllTypes
    myFilter.IncludeType msdElementTypeLineString
    myFilter.IncludeType msdElementTypeShape
    myFilter.IncludeType msdElementTypeComplexShape
    myFilter.IncludeType msdElementTypeLine
   ' myFilter.IncludeOnlyVisible
    
    Set MyEnum = ActiveModelReference.Scan(myFilter)
            While MyEnum.MoveNext
            If MyEnum.Current.Level.IsDisplayedInView(View) = True Then
                Set aCandidates(i) = MyEnum.Current
                aCandidates(i).Transform Transform3dFromMatrix3dPoint3d(Matrix3dFromScaleFactors(1, 1, 0), Point3dFromXYZ(0, 0, 0))
                i = i + 1
                ReDim Preserve aCandidates(i)
            End If
        Wend
    ReDim Preserve aCandidates(i - 1)
    
    MyPoint = Point
   ' If UserForm11.cbSetOffset.Value = True Then MyPoint = SetRegionPoint ' Если указывается оффсет вручную. то точка региона прделевается по вектору взятия дистанции
    If UserForm1.cbUseCorridor.Value = True Then GetCorridorsFromReference aCandidates, MyPoint ' Включение коридоров из референса
    If UserForm1.CheckBox_hole.Value = True Then Mhole = True
    
    
    Set oElement = GetFloodBoundary(aCandidates, Nothing, MyPoint, , Mhole, CDbl(UserForm1.tbTolerance.Text), msdFillModeFilled)
    If oElement Is Nothing Then MsgBox "Регион не построен", vbOKOnly
    'Set myReg = oElement
   ' Set shEnum = myReg.GetSubElements
       ' While shEnum.MoveNext
'            Set myRegion = ComplexShapeToShape(myReg)
'       ' Wend
'    Set MyShape = CreateShapeElement1(Nothing, myRegion.GetVertices, msdFillModeFilled)
    Set oElement.Level = ActiveSettings.Level
    ActiveModelReference.AddElement oElement
    oElement.Rewrite
    oElement.Redraw
    
    If UserForm1.cbDeletInitialElement.Value = True Then DeletInitialLine MyShape
    ActiveDesignFile.Views(View.Index).Redraw
End Sub

Private Sub IPrimitiveCommandEvents_Dynamics(Point As Point3d, ByVal View As View, ByVal DrawMode As MsdDrawingMode)

End Sub

Private Sub IPrimitiveCommandEvents_Keyin(ByVal Keyin As String)

End Sub

Private Sub IPrimitiveCommandEvents_Reset()
CommandState.StartDefaultCommand
    'Myform.InputFence CDbl(Myform.tbOffset.Text), Myform.cmbCell.Text
End Sub

Private Sub IPrimitiveCommandEvents_Start()
    ReDim aCandidates(0)
End Sub

Private Sub DeletInitialLine(mElement As Element)
    Dim myFilter As New ElementScanCriteria
    Dim MyEnum As ElementEnumerator
    Dim MyLevel As Level
    Dim MyLine As LineElement
    Dim iPoint() As Point3d
  ' Set MyLevel = Shape.Level

    myFilter.ExcludeAllTypes
  '  myFilter.ExcludeAllLevels
    myFilter.IncludeType msdElementTypeLine
    myFilter.IncludeType msdElementTypeLineString
   ' myFilter.IncludeLevel ActiveDesignFile.Levels.Find(mElement.Level.Name)
    
    Set MyEnum = ActiveModelReference.Scan(myFilter)
        While MyEnum.MoveNext
            Set MyLine = MyEnum.Current
            iPoint = MyLine.AsIntersectableElement.GetIntersectionPointsOnIntersector(oElement, Matrix3dIdentity)
            If UBound(iPoint) >= 0 Then
                ActiveModelReference.RemoveElement MyLine
            End If
        Wend
    
End Sub

Private Sub GetCorridorsFromReference(Candidates() As Element, sPoint As Point3d)
    Dim myAttach As Attachment
    Dim myFilter As New ElementScanCriteria
    Dim myElemFilter As New ElementScanCriteria
    Dim myEnumElement As ElementEnumerator
    Dim Corridors() As ShapeElement
    Dim MyElements() As Element 'Элементы для расширения
    Dim MyEnum As ElementEnumerator
    Dim iniRegion As LineElement ' Исходный регион
    Dim iPoint() As Point3d ' Точки пересечения
    Dim oElement As Element
    Dim shEnum As ElementEnumerator
    Dim myReg As ComplexElement
    
    Dim i As Integer
    Dim j As Integer
    
    ReDim Corridors(0)
    ReDim MyElements(0)
    
    Set myAttach = ActiveDesignFile.DefaultModelReference.Attachments(UserForm1.cmbReference.ListIndex + 1)
    
    
    myFilter.ExcludeAllTypes
    myFilter.ExcludeAllLevels
    
    myFilter.IncludeType msdElementTypeShape
    myFilter.IncludeLevel myAttach.Levels.FindByNumber(CLng(UserForm1.tbLevelCorridor.Text))
    
    myElemFilter.ExcludeAllLevels
    myElemFilter.ExcludeAllTypes
    
    Set MyEnum = myAttach.Scan(myFilter)
        While MyEnum.MoveNext
            Select Case MyEnum.Current.Type
                Case msdElementTypeShape
                    Set Corridors(UBound(Corridors)) = MyEnum.Current
                    ReDim Preserve Corridors(UBound(Corridors) + 1)
            End Select
        Wend
    ReDim Preserve Corridors(UBound(Corridors) - 1)
    
    j = 0
    i = (UBound(Candidates) + 1)
    For i = i To (i + UBound(Corridors))
        ReDim Preserve Candidates(UBound(Candidates) + 1)
        Set Candidates(i) = Corridors(j)
        j = j + 1
    Next i
    
 '   Set oElement = GetFloodBoundary(Candidates, Nothing, sPoint, , False, -1, msdFillModeFilled)
  '  If oElement Is Nothing Then MsgBox "Регион не построен", vbOKOnly
  '  Set myReg = oElement
  '  Set shEnum = myReg.GetSubElements
  '      While shEnum.MoveNext
  '          Set iniRegion = shEnum.Current
 '       Wend
 '   ActiveModelReference.AddElement iniRegion
 '   iniRegion.Redraw
'    Debug.Print iniRegion.Area
    
    
    
    
 '   ReDim Preserve Candidates(UBound(Candidates) - 1)
End Sub

Private Function ComplexShapeToShape(CShape As Element) As ShapeElement
    Dim MyEnum As ElementEnumerator
    Dim MyShape As ShapeElement
    Dim Verteces() As Point3d
    Dim i As Integer
    ReDim Verteces(0)
    If CShape.IsComplexShapeElement Then
        Set MyEnum = CShape.AsComplexShapeElement.GetSubElements
            While MyEnum.MoveNext
                For i = 0 To UBound(MyEnum.Current.AsVertexList.GetVertices)
                    Verteces(UBound(Verteces)) = MyEnum.Current.AsLineElement.Vertex(i + 1)
                    ReDim Preserve Verteces(UBound(Verteces) + 1)
                Next i
                ReDim Preserve Verteces(UBound(Verteces) - 1)
            Wend
     '   CShape.IsSnappable = True
        Set MyShape = CreateShapeElement1(CShape, Verteces, msdFillModeNotFilled)
        MyShape.IsSnappable = True
        Set ComplexShapeToShape = MyShape
       ' ActiveModelReference.AddElement MyShape
    ElseIf CShape.IsShapeElement Then
        Set ComplexShapeToShape = CShape.AsShapeElement
    End If
End Function

Attribute VB_Name = "UserForm1"
Attribute VB_Base = "0{DC322676-633D-4345-B3E0-DCAD22AD10A3}{82727EDB-E1F4-4F3F-84C0-43BB52947FF3}"
Attribute VB_GlobalNameSpace = False
Attribute VB_Creatable = False
Attribute VB_PredeclaredId = True
Attribute VB_Exposed = False
Attribute VB_TemplateDerived = False
Attribute VB_Customizable = False
Sub InitializationReference()
Dim MyModel As ModelReference
Dim myAttachment As Attachment
Set MyModel = ActiveDesignFile.DefaultModelReference
    For Each myAttachment In MyModel.Attachments
        Debug.Print myAttachment.AttachName
        UserForm1.cmbReference.AddItem myAttachment.AttachName
        myAttachment.LogicalName = myAttachment.AttachName
    Next
   If UserForm1.cmbReference.ListCount > 0 Then UserForm1.cmbReference.ListIndex = 0
End Sub
Private Sub CommandButton_create_Region_Click()
If UserForm1.cmbReference.Text = "" And UserForm1.cbUseCorridor.Value = True Then MsgBox "Укажите Reference"
CommandState.StartPrimitive New PCE_Create_region, True
End Sub



Private Sub UserForm_Initialize()
    InitializationReference
End Sub
