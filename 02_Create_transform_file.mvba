Attribute VB_Name = "Module1"
Option Explicit

Declare Function mdlDialog_fileCreate Lib "stdmdlbltin.dll" (ByVal _
    fileName As String, ByVal rFileH As Long, ByVal resourceId As Long, _
    ByVal suggestedFileName As String, ByVal filterString As String, _
    ByVal defaultDirectory As String, ByVal titleString As String) As Long
Sub Out()

Dim MyLine As Element
Dim StPoint() As Point3d
Dim i As Integer
Dim id As Integer
ReDim StPoint(0)
Dim SelElems As ElementEnumerator
Dim LineElement As LineElement
Dim Dx() As Double
Dim Dy() As Double
Dim Dz() As Double
ReDim Dx(0)
ReDim Dy(0)
ReDim Dz(0)
Dim MyFile As String
Dim FFile As Long
FFile = FreeFile

Dim strFName As String
Dim lngfhandle As Long
Dim lngrid As Long
Dim retVal As Long

strFName = Space(255)
id = 0
Set SelElems = ActiveModelReference.GetSelectedElements
While SelElems.MoveNext
    Set MyLine = SelElems.Current
    Select Case MyLine.Type
        Case msdElementTypeLine
            Set LineElement = MyLine
            StPoint(id) = LineElement.StartPoint
            Dx(id) = LineElement.EndPoint.X - LineElement.StartPoint.X
            Dy(id) = LineElement.EndPoint.Y - LineElement.StartPoint.Y
            Dz(id) = LineElement.EndPoint.Z - LineElement.StartPoint.Z
            id = id + 1
            ReDim Preserve StPoint(id)
            ReDim Preserve Dx(id)
            ReDim Preserve Dy(id)
            ReDim Preserve Dz(id)
            Debug.Print LineElement.EndPoint.X
            Debug.Print Dx(id - 1)
    End Select
Wend

    retVal = mdlDialog_fileCreate(strFName, lngfhandle, lngrid, "", "*.txt", "C:\", "Сохранение файла привязки")
    Select Case retVal
        Case 0 'Open
            strFName = Left(strFName, InStr(1, strFName, Chr(0)) - 1)
            MsgBox "Файл привязки сохранен:" & vbCr & strFName
        Case 1 'Cancel
            MsgBox "Файл не сохранен"
            'User hit the Cancel Button
            Exit Sub
    End Select
    
    MyFile = strFName
    Open MyFile For Output As #FFile
    For i = 0 To (id - 1)
        Print #FFile, Round(StPoint(i).X, 4) & " " & Round(StPoint(i).Y, 4) & " " & Round(Dx(i), 4) & " " & Round(Dy(i), 4) & " " & Round(Dz(i), 4)
        Debug.Print StPoint(i).X & " " & StPoint(i).Y & " " & Dx(i) & " " & Dy(i) & " " & Dz(i)
    Next i
    
End Sub
Sub Main()
MyForm.show vbModeless
ShowCommand "Создание файла привязки"
ShowPrompt "Выделите отрезки -> Сформировать"
End Sub

Attribute VB_Name = "MyForm"
Attribute VB_Base = "0{011991B7-475F-4574-BDF2-1C87A66D5EFF}{E67DB9BF-6755-4B22-9208-F34344C32F12}"
Attribute VB_GlobalNameSpace = False
Attribute VB_Creatable = False
Attribute VB_PredeclaredId = True
Attribute VB_Exposed = False
Attribute VB_TemplateDerived = False
Attribute VB_Customizable = False
Option Explicit

Private Sub cmbCreate_Click()
    Out
End Sub
