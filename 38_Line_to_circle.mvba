Attribute VB_Name = "Module1"
Sub Main()
    UserForm.Show vbModeless
End Sub

Attribute VB_Name = "UserForm"
Attribute VB_Base = "0{14F9EEAB-81D4-45F8-86FE-8C0D323F1B07}{196DBD62-1818-41D6-A1FF-5E0186BF395A}"
Attribute VB_GlobalNameSpace = False
Attribute VB_Creatable = False
Attribute VB_PredeclaredId = True
Attribute VB_Exposed = False
Attribute VB_TemplateDerived = False
Attribute VB_Customizable = False
Private Sub InitializeLevel(myCombo As ComboBox)
    Dim myLevel As Level
    
    For Each myLevel In ActiveModelReference.Levels
        myCombo.AddItem myLevel.Name
    Next
End Sub

Private Sub CommandButton_Calculate_Click()
    CalculateLengh
End Sub





Private Sub UserForm_DblClick(ByVal Cancel As MSForms.ReturnBoolean)
        InitializeLevel UserForm.ComboBox_Level
End Sub

Private Sub UserForm_Initialize()
    InitializeLevel UserForm.ComboBox_Level
End Sub

Private Sub CalculateLengh()
    Dim myEnum As ElementEnumerator
    Dim ComplexString As ElementEnumerator
    Dim myFilter As New ElementScanCriteria
    Dim mVertex() As Point3d
    Dim mCircle As EllipseElement
    Dim r As Double ' Радиус
    Dim i As Long ' Количество Linestring
    Dim j As Long ' Количество ComplexChaine
    Dim k As Long ' Количество Line
    

    If ActiveModelReference.AnyElementsSelected Then
        Set myEnum = ActiveModelReference.GetSelectedElements
    Else
        myFilter.ExcludeAllTypes
        myFilter.ExcludeAllLevels
    
        myFilter.IncludeLevel ActiveDesignFile.Levels(UserForm.ComboBox_Level.Text)
        myFilter.IncludeType msdElementTypeLineString
        myFilter.IncludeType msdElementTypeComplexString
        Set myEnum = ActiveModelReference.Scan(myFilter)
    End If
    
    r = CDbl(UserForm.TextBox_radius.Text)
    
    While myEnum.MoveNext
        Select Case myEnum.Current.Type
            Case msdElementTypeLineString
                mVertex = myEnum.Current.AsLineElement.GetVertices
                For i = 0 To UBound(mVertex)
                    Set mCircle = CreateEllipseElement2(Nothing, mVertex(i), r, r, Matrix3dIdentity)
                    ActiveModelReference.AddElement mCircle
                    mCircle.Redraw
                Next i
                
'            Case msdElementTypeComplexString
'                mVertex = myEnum.Current.AsComplexStringElement.GetVertices
'                For i = 0 To UBound(mVertex)
'                    Set mCircle = CreateEllipseElement2(Nothing, mVertex(i), r, r, Matrix3dIdentity)
'                    ActiveModelReference.AddElement mCircle
'                    mCircle.Redraw
'                Next i
'                l = l + myEnum.Current.AsComplexStringElement.Length
'                j = j + 1
'            Case msdElementTypeLine
'                l = l + myEnum.Current.AsLineElement.Length
'                k = k + 1
        End Select

    Wend
'MsgBox "Длинна: " & FormatNumber(Round(l, 2), CInt(2), vbTrue, vbFalse, vbTrue) & " м" & vbCr & "LineString: " & i & vbCr & "ComplexChain: " & j & vbCr & "Line: " & k

End Sub
