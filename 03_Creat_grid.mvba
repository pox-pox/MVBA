Attribute VB_Name = "Module1"
Option Explicit

Sub Main()
MyForm.show vbModeless
End Sub

Attribute VB_Name = "MyForm"
Attribute VB_Base = "0{A48993BA-63CA-4D5E-B87B-1B6286FCED24}{BAF5E7FF-B36D-4AD1-A96F-13822539BC10}"
Attribute VB_GlobalNameSpace = False
Attribute VB_Creatable = False
Attribute VB_PredeclaredId = True
Attribute VB_Exposed = False
Attribute VB_TemplateDerived = False
Attribute VB_Customizable = False
Option Explicit

Sub GetElement()
    Dim Element As ShapeElement
    Dim MyEnum As ElementEnumerator
    Dim i As Long   'Целое начало по X
    Dim j As Long   'Целое начало по Y
    Dim Gx As Double
    Dim Gy As Double
    Dim Grid() As Point3d
    Dim g As Long   'Количество элементов сетки
    Dim Gi As Long 'Количство крестов по X
    Dim Gj As Long  'Количество крестов по Y
    Dim dG As Double    ' Шаг сетки
    Dim Fence() As Point3d
    Dim Point As Point3d
    
    Dim pt As LineElement
    Dim cell As CellElement
   
    g = 0
    ReDim Grid(g)
    dG = CDbl(tbGrid.Text)
    Gi = 0
    Gj = 0
    
    Set MyEnum = ActiveModelReference.GetSelectedElements
        While MyEnum.MoveNext
            Set Element = MyEnum.Current
        Wend
    On Error Resume Next
        Fence = Element.GetVertices
        If Err.Number = 91 Then
            MsgBox "Выделите элемент"
        Else
            ReDim Preserve Fence(UBound(Fence()) - 1)
            i = Element.Range.Low.X \ dG
            j = Element.Range.Low.Y \ dG
            Do
            Gy = (j + Gj) * dG
            Gj = Gj + 1
                Do
                Gx = (i + Gi) * dG
                Gi = Gi + 1
                Point.X = Gx
                Point.Y = Gy
                    If Point3dInPolygonXY(Point, Fence()) = 1 Then
                        Grid(g) = Point
                        g = g + 1
                        ReDim Preserve Grid(g)
                    End If
                Loop While Gx < Element.Range.High.X
                Gi = 1
            Loop While Gy < Element.Range.High.Y
            g = g - 1
            ReDim Preserve Grid(g)
            For i = 0 To g
                Set cell = CreateCellElement3(cmbCell.Text, Grid(i), True)
                Set pt = CreateLineElement2(Nothing, Grid(i), Grid(i))
                ActiveModelReference.AddElement cell
                cell.Level = ActiveDesignFile.Levels.Find(ComboBox_Level_write.Text)
                cell.Rewrite
                cell.Redraw
            Next i
        End If
     Err.Clear
End Sub
Private Sub cnbGrid_Click()
    GetElement
End Sub

Private Sub cnbText_Click()
    Dim Element As CellElement
    Dim MyEnum As ElementEnumerator
    Dim rmX As Matrix3d
    Dim rmY As Matrix3d
    Dim txtX As TextElement
    Dim txtY As TextElement
    Dim ptX As Point3d
    Dim ptY As Point3d
    Dim i As Double 'Сдвиг подписи
    
    rmX = Matrix3dFromAxisAndRotationAngle(2, Pi / 2)
    rmY = Matrix3dFromAxisAndRotationAngle(2, 0)
    
    
    Set MyEnum = ActiveModelReference.GetSelectedElements
        While MyEnum.MoveNext
            Set Element = MyEnum.Current
            i = 5
            ptX.X = Element.Origin.X - CDbl(tbY.Text)
            ptX.Y = Element.Origin.Y + CDbl(tbX.Text)
            
            ptY.X = Element.Origin.X + CDbl(tbX.Text)
            ptY.Y = Element.Origin.Y + CDbl(tbY.Text)
            
            Set txtX = CreateTextElement1(Nothing, CStr(Element.Origin.X), ptX, rmX)
            ActiveModelReference.AddElement txtX
            txtX.Redraw
            Set txtY = CreateTextElement1(Nothing, Right(CStr(Element.Origin.Y), Len(CStr(Element.Origin.Y)) - CDbl(tbI.Text)), ptY, rmY)
            ActiveModelReference.AddElement txtY
            txtY.Redraw
        
        Wend
    
End Sub

Private Sub InitializeLevels(mComboBox As ComboBox)
  Dim myLevel As Level

  mComboBox.Clear
  For Each myLevel In ActiveDesignFile.Levels
    mComboBox.AddItem myLevel.Name
  Next
End Sub
Private Sub InitializeCellsAsAttach(mCmboBox As ComboBox)
    Dim MyCellEnum As CellInformationEnumerator
    Dim MyCell As CellInformation
    
    mCmboBox.Clear
        If IsCellLibraryAttached Then
            Set MyCellEnum = Application.GetCellInformationEnumerator(True, False)
            While MyCellEnum.MoveNext
                Set MyCell = MyCellEnum.Current
                If Not MyCell.IsShared Then mCmboBox.AddItem MyCell.Name
            Wend
        Else: MsgBox "Библиотека Cell не подключена", vbOKOnly
        End If
End Sub

Private Sub CommandButton_Del_obj_Click()
    Dim eGrid As ElementEnumerator
    Dim ePoint As ElementEnumerator
    Dim i As Long ' Счетчик
    Dim g As Double
    Dim p3d As Point3d
    
   ' IniGridEnum eGrid
    IniPointEnum ePoint
    
'    While eGrid.MoveNext
'        While ePoint.MoveNext
'            p3d.X = ePoint.Current.AsLineElement.StartPoint.X
'            p3d.Y = ePoint.Current.AsLineElement.StartPoint.Y
'            p3d.Z = 0
'            If Point3dEqualTolerance(eGrid.Current.AsCellElement.Origin, p3d, 0) = True Then
'                ActiveModelReference.RemoveElement ePoint.Current
'                ePoint.Current.Redraw
'                i = i + 1
'            End If
'        Wend
'        ePoint.Reset
'    Wend
    If tbGrid.Text <> "" Then
        g = CDbl(tbGrid.Text)
        While ePoint.MoveNext
            If ePoint.Current.AsLineElement.StartPoint.X Mod g = 0 Then
                If ePoint.Current.AsLineElement.StartPoint.Y Mod g = 0 Then
                    ActiveModelReference.RemoveElement ePoint.Current
                    ePoint.Current.Redraw
                    i = i + 1
                End If
            End If
        Wend
        MsgBox "Удалено: " & i
    Else
        MsgBox "Задайте шаг сетки"
    End If
End Sub

Private Sub IniGridEnum(ByRef mEnum As ElementEnumerator)
    Dim mFilter As New ElementScanCriteria
    
    mFilter.ExcludeAllLevels
    mFilter.ExcludeAllTypes
    
    mFilter.IncludeLevel ActiveDesignFile.Levels.Find(ComboBox_Level_write.Text)
    mFilter.IncludeType msdElementTypeCellHeader
    
    Set mEnum = ActiveModelReference.Scan(mFilter)
    
End Sub
Private Sub IniPointEnum(ByRef mEnum As ElementEnumerator)
    Dim mFilter As New ElementScanCriteria
    
    mFilter.ExcludeAllLevels
    mFilter.ExcludeAllTypes
    
    mFilter.IncludeLevel ActiveDesignFile.Levels.Find(ComboBox_Level_delObj.Text)
    mFilter.IncludeType msdElementTypeLine
    
    Set mEnum = ActiveModelReference.Scan(mFilter)
End Sub
Private Sub UserForm_Initialize()
    InitializeCellsAsAttach cmbCell
    InitializeLevels ComboBox_Level_delObj
    InitializeLevels ComboBox_Level_write
End Sub
