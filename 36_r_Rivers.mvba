Attribute VB_Name = "LCE_DrawH"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Dim mShape As ShapeElement
Dim mLine As LineElement

Private Sub ILocateCommandEvents_Accept(ByVal Element As Element, Point As Point3d, ByVal View As View)
    Dim mH As TextElement
    Dim i As Long
    
    Select Case Element.Type
        Case msdElementTypeShape
            For i = 1 To Element.AsShapeElement.VerticesCount - 1
                Set mH = CreateTextElement1(Nothing, Round(Element.AsLineElement.Vertex(i).Z, 2), Element.AsShapeElement.Vertex(i), Matrix3dIdentity)
                ActiveModelReference.AddElement mH
                mH.Level = ActiveModelReference.Levels.Find("Default")
                mH.Rewrite
                mH.Redraw
            Next i
        Case msdElementTypeLineString
            For i = 1 To Element.AsLineElement.VerticesCount
                Set mH = CreateTextElement1(Nothing, Round(Element.AsLineElement.Vertex(i).Z, 2), Element.AsLineElement.Vertex(i), Matrix3dIdentity)
                ActiveModelReference.AddElement mH
                mH.Level = ActiveModelReference.Levels.Find("Default")
                mH.Rewrite
                mH.Redraw
            Next i
    End Select
End Sub

Private Sub ILocateCommandEvents_Cleanup()

End Sub

Private Sub ILocateCommandEvents_Dynamics(Point As Point3d, ByVal View As View, ByVal DrawMode As MsdDrawingMode)

End Sub

Private Sub ILocateCommandEvents_LocateFailed()
  '  MsgBox "Укажите Shape"
End Sub

Private Sub ILocateCommandEvents_LocateFilter(ByVal Element As Element, Point As Point3d, Accepted As Boolean)

Accepted = False

    If Element.Type = msdElementTypeShape Or Element.Type = msdElementTypeLineString Then
        
        Accepted = True
    
    End If

End Sub

Private Sub ILocateCommandEvents_LocateReset()

End Sub

Private Sub ILocateCommandEvents_Start()
CommandState.EnableAccuSnap
    ShowCommand "Пописать высоты"
    ShowPrompt "Элемент"
End Sub

Attribute VB_Name = "LCE_rLine"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents
Private rLine As LineElement


Private Sub ILocateCommandEvents_Accept(ByVal Element As Element, Point As Point3d, ByVal View As View)
    Dim i As Long
    Dim s As Long
    Dim Seg() As Point3d
    Dim hPoint As Point3d
    Dim ml As LineElement
    Dim rLine3d As LineElement
    Dim oContext As New CopyContext

    
    Set rLine3d = ActiveModelReference.CopyElement(rLine, oContext)
    
    If ShapeTrue Then
        For i = 1 To rShape.VerticesCount - 1
            
            Seg = GetClosestSegment3d(rLine, rShape.Vertex(i))
            hPoint = Dist_Segment_to_Point3d(Seg(0), Seg(1), rShape.Vertex(i))
            
           
           
            Set ml = CreateLineElement2(Nothing, hPoint, rShape.Vertex(i))
            hPoint = GetIntersection(rLine3d, ml)
            
'             Dim inter As LineElement
'            Set inter = CreateLineElement2(Nothing, hPoint, hPoint)
'            inter.LineWeight = 8
'            ActiveModelReference.AddElement inter
'            inter.Redraw
'
            
'            ActiveModelReference.AddElement ml
'            ml.Redraw
            hPoint.X = rShape.Vertex(i).X
            hPoint.Y = rShape.Vertex(i).Y
            rShape.ModifyVertex (i - 1), hPoint
            rShape.Rewrite
            rShape.Redraw
        Next i
    Else
        For i = 1 To rPolyLine.VerticesCount
            
            Seg = GetClosestSegment3d(rLine, rPolyLine.Vertex(i))
            hPoint = Dist_Segment_to_Point3d(Seg(0), Seg(1), rPolyLine.Vertex(i))
            Set ml = CreateLineElement2(Nothing, hPoint, rShape.Vertex(i))
            hPoint = GetIntersection(rLine3d, ml)
'            ActiveModelReference.AddElement ml
'            ml.Redraw
            hPoint.X = rPolyLine.Vertex(i).X
            hPoint.Y = rPolyLine.Vertex(i).Y
            rPolyLine.ModifyVertex (i - 1), hPoint
            rPolyLine.Rewrite
            rPolyLine.Redraw
        Next i
    End If
    ActiveModelReference.RemoveElement rLine3d
End Sub

Private Sub ILocateCommandEvents_Cleanup()

End Sub

Private Sub ILocateCommandEvents_Dynamics(Point As Point3d, ByVal View As View, ByVal DrawMode As MsdDrawingMode)

End Sub

Private Sub ILocateCommandEvents_LocateFailed()

End Sub

Private Sub ILocateCommandEvents_LocateFilter(ByVal Element As Element, Point As Point3d, Accepted As Boolean)
    Accepted = False

If Element.Type = msdElementTypeLineString Or Element.Type = msdElementTypeLine Then
        Set rLine = Element.AsLineElement
        Accepted = True
    End If

End Sub

Private Sub ILocateCommandEvents_LocateReset()

End Sub

Private Sub ILocateCommandEvents_Start()
    ShowCommand "Выравнивание контура рек"
    ShowPrompt "Укажите rLine"
End Sub
Private Function GetIntersection(mLineString As LineElement, mLine As LineElement) As Point3d
    Dim pPoint() As Point3d
    
    pPoint = mLineString.AsIntersectableElement.GetIntersectionPoints(mLine, Matrix3dIdentity)
    If UBound(pPoint) <> -1 Then
        GetIntersection = pPoint(0)
    End If
End Function

Function GetClosestSegment3d(ByVal iLine As LineElement, iPoint As Point3d) As Point3d()
    Dim i As Long
    Dim Segment(0 To 1) As Point3d ' 0 - start , 1 - end
    iLine.Transform Transform3dFromMatrix3dPoint3d(Matrix3dFromScaleFactors(1, 1, 0), Point3dFromXYZ(0, 0, 0)) ''''' Линия в 2D
    i = iLine.GetClosestVertex(iPoint)
        If i = 0 Then
            Segment(0) = iLine.Vertex(1)
            Segment(1) = iLine.Vertex(2)
        ElseIf i = (iLine.VerticesCount - 1) Then
            Segment(0) = iLine.Vertex((iLine.VerticesCount) - 1)
            Segment(1) = iLine.Vertex(iLine.VerticesCount)
        Else
            i = i + 1
            If Dist_Segment_to_Point(iLine.Vertex(i), iLine.Vertex(i + 1), iPoint) >= Dist_Segment_to_Point(iLine.Vertex(i - 1), iLine.Vertex(i), iPoint) Then
                Segment(0) = iLine.Vertex(i - 1)
                Segment(1) = iLine.Vertex(i)
            Else
                Segment(0) = iLine.Vertex(i)
                Segment(1) = iLine.Vertex(i + 1)
            End If
        End If
    GetClosestSegment3d = Segment
End Function

Private Function Dist_Segment_to_Point3d(StartPoint As Point3d, EndPoint As Point3d, iPoint As Point3d) As Point3d
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    
    vPoint = Vector3dSubtractPoint3dPoint3d(iPoint, StartPoint)
    vLine = Vector3dSubtractPoint3dPoint3d(EndPoint, StartPoint)
    
    c1 = Vector3dDotProduct(vPoint, vLine)
    c2 = Vector3dDotProduct(vLine, vLine)
        If c1 <= 0 Then
            Dist_Segment_to_Point3d = StartPoint
        ElseIf c2 <= c1 Then
            Dist_Segment_to_Point3d = EndPoint
        Else
            k = c1 / c2
            vProject = Vector3dScale(vLine, k)
            pProject = Vector3dAdd(Vector3dFromPoint3d(StartPoint), vProject)
            Dist_Segment_to_Point3d = Point3dFromVector3d(pProject)
        End If
End Function

Private Function Dist_Segment_to_Point(StartPoint As Point3d, EndPoint As Point3d, iPoint As Point3d) As Double
    Dim vPoint As Vector3d
    Dim vLine As Vector3d
    Dim vProject As Vector3d
    Dim i As Long ' Индекс билжайшего вертекса
    Dim c1 As Double 'Скалярное произведение vPoint x vLine
    Dim c2 As Double 'Скалярное произведение vline x vLine
    Dim k As Double ' Коэффециент проекции
    Dim pProject As Vector3d
    
    vPoint = Vector3dSubtractPoint3dPoint3d(iPoint, StartPoint)
    vLine = Vector3dSubtractPoint3dPoint3d(EndPoint, StartPoint)
    
    c1 = Vector3dDotProduct(vPoint, vLine)
    c2 = Vector3dDotProduct(vLine, vLine)
        If c1 <= 0 Then
            Dist_Segment_to_Point = Point3dDistance(StartPoint, iPoint)
        ElseIf c2 <= c1 Then
            Dist_Segment_to_Point = Point3dDistance(EndPoint, iPoint)
        Else
            k = c1 / c2
            vProject = Vector3dScale(vLine, k)
            pProject = Vector3dAdd(Vector3dFromPoint3d(StartPoint), vProject)
            Dist_Segment_to_Point = Point3dDistance(Point3dFromVector3d(pProject), iPoint)
        End If
End Function

Attribute VB_Name = "LCE_rShape"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements ILocateCommandEvents


Private Sub ILocateCommandEvents_Accept(ByVal Element As Element, Point As Point3d, ByVal View As View)
    CommandState.StartLocate New LCE_rLine
End Sub

Private Sub ILocateCommandEvents_Cleanup()

End Sub

Private Sub ILocateCommandEvents_Dynamics(Point As Point3d, ByVal View As View, ByVal DrawMode As MsdDrawingMode)

End Sub

Private Sub ILocateCommandEvents_LocateFailed()
  '  MsgBox "Укажите Shape"
End Sub

Private Sub ILocateCommandEvents_LocateFilter(ByVal Element As Element, Point As Point3d, Accepted As Boolean)

Accepted = False

    If Element.Type = msdElementTypeShape Then
        Set rShape = Element.AsShapeElement
        rShape.Transform Transform3dFromMatrix3dPoint3d(Matrix3dFromScaleFactors(1, 1, 0), Point3dFromXYZ(0, 0, 0)) ''''' Линия в 2D
        ShapeTrue = True
        Accepted = True
    ElseIf Element.Type = msdElementTypeLineString Then
        Set rPolyLine = Element.AsLineElement
        rPolyLine.Transform Transform3dFromMatrix3dPoint3d(Matrix3dFromScaleFactors(1, 1, 0), Point3dFromXYZ(0, 0, 0)) ''''' Линия в 2D
        ShapeTrue = False
        Accepted = True
    End If

End Sub

Private Sub ILocateCommandEvents_LocateReset()

End Sub

Private Sub ILocateCommandEvents_Start()
CommandState.EnableAccuSnap
    ShowCommand "Выравнивание контура рек"
    ShowPrompt "Укажите shape реки"
End Sub

Attribute VB_Name = "Module1"
Option Explicit



Public rShape As ShapeElement
Public rPolyLine As LineElement
Public ShapeTrue As Boolean

Sub main()
    UserForm1.Show vbModeless
End Sub

Attribute VB_Name = "UserForm1"
Attribute VB_Base = "0{C304981F-513B-4425-B51C-A6BBDE644768}{7EB03D5C-129C-492C-B2BF-96029AA13A5C}"
Attribute VB_GlobalNameSpace = False
Attribute VB_Creatable = False
Attribute VB_PredeclaredId = True
Attribute VB_Exposed = False
Attribute VB_TemplateDerived = False
Attribute VB_Customizable = False
Option Explicit

Private Sub CommandButton1_Click()
    CommandState.StartLocate New LCE_rShape
End Sub

Private Sub CommandButton2_Click()
    CommandState.StartLocate New LCE_DrawH
End Sub
