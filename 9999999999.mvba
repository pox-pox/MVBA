Attribute VB_Name = "Module1"
Sub main()

    Dim myElement As Element
    Dim myEnum As ElementEnumerator
    Dim mFilter As New ElementScanCriteria
    Dim sm As ElementEnumerator
    
    'mFilter.ExcludeAllLevels
  '  mFilter.ExcludeAllTypes
    
   ' mFilter.IncludeLevel ActiveDesignFile.Levels("0301000")
  '  mFilter.IncludeType msdElementTypeSolid
    
    Set myEnum = ActiveModelReference.Scan(mFilter)
    
    While myEnum.MoveNext
        Select Case myEnum.Current.Type
            Case msdElementTypeCellHeader
'                ActiveModelReference.Activate
'                CommandState.UpdateElementDependencyState
                ActiveModelReference.SelectElement myEnum.Current
                
'                Debug.Print myEnum.Current.Type
'                ActiveModelReference.ReplaceElement myEnum.Current, myEnum.Current.AsSmartSolidElement.FacetSolidAsMesh(100, 100, 1, 5)
                
                
            End Select
    Wend
    CadInputQueue.SendCommand "FACET CREATE"
    CadInputQueue.SendDataPoint Point3dFromXYZ(0, 0, 0), 1
    CommandState.StartDefaultCommand
    
End Sub
