Attribute VB_Name = "Module1"
Option Explicit

Sub Main()
    UserForm1.Show vbModeless
End Sub

Attribute VB_Name = "UserForm1"
Attribute VB_Base = "0{4E5FD126-A707-4DFE-93E6-0BB3145C1D6D}{1964B45F-4DFF-46BD-9FB3-DE60DE728D97}"
Attribute VB_GlobalNameSpace = False
Attribute VB_Creatable = False
Attribute VB_PredeclaredId = True
Attribute VB_Exposed = False
Attribute VB_TemplateDerived = False
Attribute VB_Customizable = False
Option Explicit

Sub InizialisationCells()
    Dim MyEnum As ElementEnumerator
    Dim myFilter As New ElementScanCriteria
    Dim MyCell As SharedCellElement
    Dim i As Integer
    Dim bool As Boolean

    UserForm1.ComboBox_cell.Clear
    myFilter.ExcludeAllTypes
    'myFilter.IncludeType msdElementTypeCellHeader
    myFilter.IncludeType msdElementTypeSharedCell
    
    Set MyEnum = ActiveModelReference.Scan(myFilter)
    
    While MyEnum.MoveNext
        Set MyCell = MyEnum.Current
            Do
                For i = 0 To UserForm1.ComboBox_cell.ListCount - 1
                    If UserForm1.ComboBox_cell.List(i, 0) = MyCell.Name Then
                        Exit Do
                    End If
                Next i
                UserForm1.ComboBox_cell.AddItem MyCell.Name
        Loop While bool = True
    Wend
End Sub

Private Sub CommandButton_find_Click()
    FindText
End Sub

Private Sub UserForm_Initialize()
    InizialisationCells
End Sub

Sub FindText()
    Dim MyEnum As ElementEnumerator
    Dim myFilter As New ElementScanCriteria
    Dim MyCell As SharedCellElement
    
    Dim MyEnumT As ElementEnumerator
    Dim myFilterT As New ElementScanCriteria
    Dim MyText As TextElement
    Dim myTxtArr() As Element
    Dim i As Double
    
    Dim minDist As Double
    Dim curDist As Double
    Dim Roun As Double
    Dim rng As Range3d
    Dim fText As TextElement
    Dim DistL As LineElement
        
    minDist = CDbl(TextBox_minDist.Text)
    
    myFilter.ExcludeAllTypes
    myFilter.IncludeType msdElementTypeSharedCell
    
    myFilterT.ExcludeAllTypes
    myFilterT.IncludeType msdElementTypeText
    
    Set MyEnum = ActiveModelReference.Scan(myFilter)
    Set MyEnumT = ActiveModelReference.Scan(myFilterT)
    myTxtArr = MyEnumT.BuildArrayFromContents
    
    While MyEnum.MoveNext
        Set MyCell = MyEnum.Current
            For i = 0 To UBound(myTxtArr)
                curDist = Point3dDistanceXY(MyCell.Origin, myTxtArr(i).AsTextElement.Origin)
                
                rng = myTxtArr(i).AsTextElement.Boundary
              '  rng.Low = myTxtArr(i).AsTextElement.Origin
                If Range3dContainsPoint3d(rng, Point3dFromXY(MyCell.Origin.X, MyCell.Origin.Y)) Then
                    Set fText = myTxtArr(i).AsTextElement
                    Exit For
                End If
                    If curDist < minDist Then
                        Set fText = myTxtArr(i).AsTextElement
                        minDist = curDist
                    End If
                DrawPoint rng.Low, 1
                DrawPoint rng.High, 3
            Next i
        On Error Resume Next
        
        If Not fText Is Nothing Then
        Set DistL = CreateLineElement2(Nothing, MyCell.Origin, fText.Origin)
        ActiveModelReference.AddElement DistL
            Roun = Round(MyCell.Origin.Z, 2)
            If Abs((Roun - CDbl(fText.Text))) > CDbl(TextBox_tolerance.Text) Then
                DistL.Color = 3
                DistL.LineWeight = 3
            End If
        DistL.Redraw
        DistL.Rewrite
        minDist = CLng(TextBox_minDist.Text)
        Set fText = Nothing
        End If
        
    Wend
        
End Sub
Function RoundMath(Tochn As Double, iR As Integer) As Double
    Dim Rounded As Double, HTochn As Double, TTochn As Double
    Dim HTochnCroped As Long, TTochnCroped As Long, IDelta As Integer
    HTochn = Tochn * 10 ^ iR
    TTochn = HTochn * 10
    HTochnCroped = Fix(HTochn)
    TTochnCroped = HTochnCroped * 10
    IDelta = TTochn - TTochnCroped
 
    If (IDelta >= 5) Then
        Rounded = ((HTochnCroped + 1) / (10 ^ iR))
    Else
        Rounded = (HTochnCroped / (10 ^ iR))
    End If
 
    RoundMath = Rounded
End Function

Sub DrawPoint(mPoint As Point3d, col As Integer)
    Dim myLine As LineElement
    
    Set myLine = CreateLineElement2(Nothing, mPoint, mPoint)
    ActiveModelReference.AddElement myLine
    myLine.LineWeight = 3
    myLine.Color = col
    myLine.Rewrite
    myLine.Redraw
    
End Sub
