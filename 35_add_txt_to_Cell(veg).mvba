Attribute VB_Name = "Module1"
Option Explicit

Sub main()
    UserForm1.Show vbModeless
End Sub

Attribute VB_Name = "UserForm1"
Attribute VB_Base = "0{F70AA9D4-3CCE-4A36-930D-5F213C18F6D3}{8BA0CB3B-CF25-4529-B872-36F8C27C53A6}"
Attribute VB_GlobalNameSpace = False
Attribute VB_Creatable = False
Attribute VB_PredeclaredId = True
Attribute VB_Exposed = False
Attribute VB_TemplateDerived = False
Attribute VB_Customizable = False
Option Explicit

Private Sub CommandButton1_Click()
AddText
End Sub

Private Sub TextBox_text_Change()

End Sub

Private Sub UserForm_Click()

End Sub

Private Sub UserForm_Initialize()
    InizialisationCells
End Sub

Sub InizialisationCells()
    Dim MyEnum As ElementEnumerator
    Dim myFilter As New ElementScanCriteria
    Dim myCell As CellElement
    Dim i As Integer
    Dim bool As Boolean

    UserForm1.ComboBox_cells.Clear
    myFilter.ExcludeAllTypes
    myFilter.IncludeType msdElementTypeCellHeader
    
    Set MyEnum = ActiveModelReference.Scan(myFilter)
    
    While MyEnum.MoveNext
        Set myCell = MyEnum.Current
            Do
                For i = 0 To UserForm1.ComboBox_cells.ListCount - 1
                    If UserForm1.ComboBox_cells.List(i, 0) = myCell.Name Then
                        Exit Do
                    End If
                Next i
                UserForm1.ComboBox_cells.AddItem myCell.Name
        Loop While bool = True
    Wend
           
End Sub

Sub AddText()
    Dim MyEnum As ElementEnumerator
    Dim myFilter As New ElementScanCriteria
    Dim myCell As CellElement
    Dim mText As TextElement
    Dim lvl As Level
    Dim insPoint As Point3d
    Dim h As Long
    Dim l As Long
    
    If UserForm1.ComboBox_cells.Text = "" Then
        MsgBox "Выберите Cell"
    End If

    myFilter.ExcludeAllTypes
    myFilter.IncludeType msdElementTypeCellHeader
    
    Set MyEnum = ActiveModelReference.Scan(myFilter)
    
    While MyEnum.MoveNext
        Set myCell = MyEnum.Current
            If myCell.Name = UserForm1.ComboBox_cells.Text Then
                insPoint.X = myCell.Range.Low.X
                
                insPoint.Y = (myCell.Range.Low.Y + myCell.Range.High.Y) * 0.5
                Set mText = CreateTextElement1(Nothing, UserForm1.TextBox_text.Text, insPoint, Matrix3dIdentity)
                h = ActiveSettings.TextStyle.Height
                l = mText.Range.High.X - mText.Range.Low.X
                mText.Move Point3dFromXY(-l - CDbl(UserForm1.TextBox_offset.Text), -h * 0.5)
                ActiveModelReference.AddElement mText
               
                mText.Rewrite
                mText.Redraw
                
                
    
'
'                Set myPoint = CreateLineElement2(myCell, myCell.Origin, myCell.Origin)
'                myPoint.Level = ActiveDesignFile.Levels.Find(ActiveSettings.Level.Name)
'                ActiveModelReference.AddElement myPoint
'                myPoint.Redraw
                    
            End If
    Wend
End Sub
