Attribute VB_Name = "GetPictureCell"
Option Explicit

Sub DrawCellPreview(CellName As String)
    Dim width As Long
    Dim height As Long
    Dim MyCell As CellElement
    Dim MyMatrix As Matrix3d
    Dim MyTransform As Transform3d
    
    Dim Op As Point3d
    On Error Resume Next
    width = PointsToPixelsX(MyForm.CellPreview.width)
    height = PointsToPixelsY(MyForm.CellPreview.height)
    If CellName <> "" Then
            MyMatrix = Matrix3dFromAxisAndRotationAngle(0, Pi / 2)
            Set MyCell = CreateCellElement3(CellName, Op, True)
            
            Set MyForm.CellPreview.Picture = MyCell.GetPicture(width * 0.77, height * 0.77, True)
            MyTransform = Transform3dFromMatrix3dPoint3d(MyMatrix, MyCell.origin)
            MyCell.transform MyTransform
            Set MyForm.CellPreviewTop.Picture = MyCell.GetPicture(width * 0.37, height * 0.37, True)
            
            MyMatrix = Matrix3dFromMatrix3dTimesMatrix3d(MyMatrix, Matrix3dFromAxisAndRotationAngle(1, Pi / 4))
            MyMatrix = Matrix3dFromMatrix3dTimesMatrix3d(MyMatrix, Matrix3dFromAxisAndRotationAngle(2, Pi / 4))
            MyTransform = Transform3dFromMatrix3dPoint3d(MyMatrix, MyCell.origin)
            MyCell.transform MyTransform
            Set MyForm.CellPreviewTop45.Picture = MyCell.GetPicture(width * 0.37, height * 0.37, True)
    End If
End Sub

Attribute VB_Name = "LCE_CreateArrow"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private stPoint As Point3d 'Главная точка опоры, начальная точка установки стрелок
Private retPoint As Point3d ' Точка для возвратной стрелки
Private retBoolean As Boolean ' Условие для указания первого cell

Implements ILocateCommandEvents

Private Sub ILocateCommandEvents_Accept(ByVal Element As Element, Point As Point3d, ByVal View As View)
    Dim arrowCell As CellElement
    Dim oPoint As Point3d ' ответная точка
    Dim RotationMatrix As Matrix3d
    Dim Sc As Point3d
    Sc.X = 1
    Sc.Y = 1
    Sc.Z = 1
    RotationMatrix = Matrix3dFromAxisAndRotationAngle(2, MyModule.AngleTxt(stPoint, Point))
    Set arrowCell = CreateCellElement2(MyForm.cmbCell.Text, stPoint, Sc, True, RotationMatrix)
    arrowCell.Level = ActiveDesignFile.Levels.Find(ActiveSettings.Level.Name)
    ActiveModelReference.AddElement arrowCell
    arrowCell.Redraw
    retPoint = stPoint
End Sub
Private Sub ILocateCommandEvents_Cleanup()

End Sub

Private Sub ILocateCommandEvents_Dynamics(Point As Point3d, ByVal View As View, ByVal DrawMode As MsdDrawingMode)
    Dim arrowCell As CellElement
    Dim RotationMatrix As Matrix3d
    Dim Sc As Point3d
    Sc.X = 1
    Sc.Y = 1
    Sc.Z = 1
    RotationMatrix = Matrix3dFromAxisAndRotationAngle(2, MyModule.AngleTxt(stPoint, Point))
    Set arrowCell = CreateCellElement2(MyForm.cmbCell.Text, stPoint, Sc, True, RotationMatrix)
    arrowCell.Redraw DrawMode
End Sub

Private Sub ILocateCommandEvents_LocateFailed()
    CommandState.StartLocate Me
End Sub

Private Sub ILocateCommandEvents_LocateFilter(ByVal Element As Element, Point As Point3d, Accepted As Boolean)
   Dim MyCell As CellElement
   Accepted = False
   Dim arrowCell As CellElement
   Dim tarCell As CellElement ' Cell
   Dim oPoint As Point3d ' ответная точка
   Dim RotationMatrix As Matrix3d
   Dim Sc As Point3d
   Sc.X = 1
   Sc.Y = 1
   Sc.Z = 1
    
   Set tarCell = Element

   If Element.IsCellElement = True Then
        Set MyCell = Element
        Accepted = True
        stPoint = MyCell.origin
        ShowCommand "Стрелки на опоре"
        If retBoolean = True And tarCell.Name <> MyForm.cmbCell.Text Then
            Set tarCell = Element
            RotationMatrix = Matrix3dFromAxisAndRotationAngle(2, MyModule.AngleTxt(stPoint, retPoint))
            Set arrowCell = CreateCellElement2(MyForm.cmbCell.Text, stPoint, Sc, True, RotationMatrix)
            arrowCell.Level = ActiveDesignFile.Levels.Find(ActiveSettings.Level.Name)
            ActiveModelReference.AddElement arrowCell
            arrowCell.Redraw
        End If
        CommandState.StartDynamics
        retBoolean = True
    End If
End Sub

Private Sub ILocateCommandEvents_LocateReset()
    CommandState.StartDefaultCommand
End Sub

Private Sub ILocateCommandEvents_Start()
    CommandState.EnableAccuSnap
End Sub

Attribute VB_Name = "MyForm"
Attribute VB_Base = "0{B49E199C-537A-40B0-9EFE-AE43CA692971}{03E30FD4-1393-4F47-9336-D66D49599122}"
Attribute VB_GlobalNameSpace = False
Attribute VB_Creatable = False
Attribute VB_PredeclaredId = True
Attribute VB_Exposed = False
Attribute VB_TemplateDerived = False
Attribute VB_Customizable = False
Option Explicit
Private Sub cmbPArrow_Click()
    CommandState.StartLocate New LCE_CreateArrow
End Sub

Private Sub CheckBox_cross_view_Change()
    If CheckBox_cross_view.Value = True Then
        ComboBox_inView.Enabled = True
        ComboBox_CrossView.Enabled = True
    Else
        ComboBox_inView.Enabled = False
        ComboBox_CrossView.Enabled = False
    End If
End Sub


Private Sub cmbCell_Change()
    GetPictureCell.DrawCellPreview MyForm.cmbCell.Text
End Sub
Private Sub cmbCell_DblClick(ByVal Cancel As MSForms.ReturnBoolean)
    UserForm_Initialize
End Sub
Private Sub cmpPlace_Click()
    Set mComboBox = cmbCell
    CommandState.StartPrimitive New PCE_PlaceCellRotate, True
End Sub
Private Sub cmbCell_MouseDown(ByVal Button As Integer, ByVal Shift As Integer, ByVal X As Single, ByVal Y As Single)
    GetPictureCell.DrawCellPreview MyForm.cmbCell.Text
End Sub
Private Sub cmbCell2_Change()
    GetPictureCell.DrawCellPreview MyForm.cmbCell2.Text
End Sub
Private Sub cmbCell2_MouseDown(ByVal Button As Integer, ByVal Shift As Integer, ByVal X As Single, ByVal Y As Single)
     GetPictureCell.DrawCellPreview MyForm.cmbCell2.Text
End Sub
Private Sub cmpPlace2_Click()
    Set mComboBox = cmbCell2
    CommandState.StartPrimitive New PCE_PlaceCellRotate, True
End Sub
Private Sub cmbCell3_Change()
    GetPictureCell.DrawCellPreview MyForm.cmbCell3.Text
End Sub
Private Sub cmbCell3_MouseDown(ByVal Button As Integer, ByVal Shift As Integer, ByVal X As Single, ByVal Y As Single)
     GetPictureCell.DrawCellPreview MyForm.cmbCell3.Text
End Sub
Private Sub cmpPlace3_Click()
    Set mComboBox = cmbCell3
    CommandState.StartPrimitive New PCE_PlaceCellRotate, True
End Sub
Private Sub ComboBox_CrossView_DblClick(ByVal Cancel As MSForms.ReturnBoolean)
    UserForm_Initialize
End Sub
Private Sub ComboBox_inView_DblClick(ByVal Cancel As MSForms.ReturnBoolean)
    UserForm_Initialize
End Sub
Private Sub UserForm_Initialize()
    Dim MyCellEnum As CellInformationEnumerator
    Dim MyCell As CellInformation
    If IsCellLibraryAttached Then
    cmbCell.Clear
    cmbCell2.Clear
    cmbCell3.Clear
            Set MyCellEnum = Application.GetCellInformationEnumerator(False, False)
            While MyCellEnum.MoveNext
                Set MyCell = MyCellEnum.Current
                cmbCell.AddItem MyCell.Name
                cmbCell2.AddItem MyCell.Name
                cmbCell3.AddItem MyCell.Name
            Wend
        Else: MsgBox "Библиотека Cell не подключена", vbOKOnly
    End If
    IniNumView ComboBox_inView
    IniNumView ComboBox_CrossView
    
End Sub
Private Sub IniNumView(mComboBox As ComboBox)
    Dim i As Integer
    
    mComboBox.Clear
    For i = 1 To 8
        If ActiveDesignFile.Views(i).IsOpen Then
            mComboBox.AddItem i
        End If
    Next i
End Sub

Attribute VB_Name = "MyModule"
Option Explicit
Public Reset As Boolean
Public PTstart As Point3d
Public PTend As Point3d
Public ID As Integer
Public mComboBox As ComboBox

'
'Public Sub GetXYZ()
'    Dim myCIQ As CadInputQueue
'    Dim myCIM As CadInputMessage
'    Set myCIQ = CadInputQueue
'    Reset = False
'    'ShowCommand "Нанесение текста"
'    'ShowPrompt "Укажите начальную точку"
'    Set myCIM = myCIQ.GetInput(msdCadInputTypeDataPoint, msdCadInputTypeReset)
'        Select Case myCIM.InputType
'            Case msdCadInputTypeReset
'                Exit Sub
'            Case msdCadInputTypeDataPoint
'                PTstart = myCIM.Point
'        End Select
'    CadInputQueue.SendCommand "PLACE Line"
'    CadInputQueue.SendDataPoint PTstart
'    'ShowCommand "Нанесение текста"
'    'ShowPrompt "Укажите конечную точку"
'    Set myCIM = myCIQ.GetInput
'        Select Case myCIM.InputType
'            Case msdCadInputTypeReset
'                Reset = True
'                Exit Sub
'            Case msdCadInputTypeDataPoint
'                PTend = myCIM.Point
'        End Select
'End Sub
Sub main()
    MyForm.Show vbModeless
End Sub
Function AngleTxt(pSt As Point3d, pEnd As Point3d) As Double
Dim dAng As Double
Dim Angel As Double
Dim ang As Double
Dim dx As Double
Dim dy As Double
dx = pEnd.X - pSt.X
dy = pEnd.Y - pSt.Y
If dy <> 0 Then
    ang = Atn(dx / dy)
    If dx >= 0 And dy > 0 Then
        dAng = ang
    ElseIf dx >= 0 And dy < 0 Then
        dAng = ang + Pi
    ElseIf dx < 0 And dy < 0 Then
        dAng = ang + Pi
    ElseIf dx < 0 And dy > 0 Then
        dAng = ang + 2 * Pi
    End If
ElseIf dy = 0 Then

    If dx > 0 Then
        dAng = Pi / 2
    ElseIf dx < 0 Then
        dAng = 3 * Pi / 4
    End If
End If
Angel = Pi / 2 - dAng
AngleTxt = Angel
End Function

Attribute VB_Name = "PCE_PlaceCellRotate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Private bPoint          As Point3d ' Точка вставки Cell
Private fdPoint         As Point3d '
Private FirstPoint      As Boolean ' Проверка на первую точку
Private Second          As Boolean
Private moveCell        As Boolean
Private CellName        As String
Private MyCell          As CellElement
Private prPointOnPlan   As Point3d
Private rotation        As Matrix3d
Private dRotation       As Matrix3d
Implements IPrimitiveCommandEvents
Private Sub IPrimitiveCommandEvents_Cleanup()
End Sub

Private Sub IPrimitiveCommandEvents_DataPoint(Point As Point3d, ByVal View As View)
Dim tmpCell         As CellElement
Dim rotation        As Matrix3d
Dim RotationMatrix  As Matrix3d
Dim OriginAccu      As Point3d
Dim oClone          As Element

Dim origin          As LineElement

    If FirstPoint = False And Second = False Then
        bPoint = Point
        FirstPoint = True
        If MyForm.CheckBox_cross_view.Value = True Then
            CrossSection CInt(MyForm.ComboBox_inView.Text), CInt(MyForm.ComboBox_CrossView.Text)
        End If
    ElseIf FirstPoint = True Then
        dRotation = Matrix3dInverse(View.rotation)
        Set MyCell = CreateCellElement2(mComboBox.Text, bPoint, Point3dOne, True, dRotation)
        MyCell.transform SecondRotate(View, Point)
        ActiveModelReference.AddElement MyCell
        MyCell.Redraw
        Second = True
        moveCell = True
        FirstPoint = False
        fdPoint = Point
    ElseIf moveCell = True Then
            MyCell.Redraw msdDrawingModeTemporaryErase
            MyCell.Move Point3dSubtract(ActiveDepthDraw(View, bPoint, Point), bPoint)
            MyCell.Redraw msdDrawingModeNormal
            MyCell.Rewrite
            fdPoint = Point3dAddPoint3dVector3d(fdPoint, Vector3dSubtractPoint3dPoint3d(ActiveDepthDraw(View, bPoint, Point), bPoint))
            bPoint = ActiveDepthDraw(View, bPoint, Point)
            moveCell = False
    ElseIf Second = True Then
        Set tmpCell = ActiveModelReference.GraphicalElementCache.GetLastValidElement.AsCellElement
        ActiveModelReference.RemoveElement tmpCell
        tmpCell.Redraw
        Set MyCell = CreateCellElement2(mComboBox.Text, bPoint, Point3dOne, True, dRotation)
        MyCell.transform SecondRotate(View, ActiveDepthDraw(View, bPoint, Point))
        ActiveModelReference.AddElement MyCell
        MyCell.Redraw
    End If

End Sub

Private Sub IPrimitiveCommandEvents_Dynamics(Point As Point3d, ByVal View As View, ByVal DrawMode As MsdDrawingMode)
    Dim transform As Transform3d
    Dim RotationMatrix As Matrix3d
    Dim oClone          As Element
    
        If FirstPoint = False And Second = False Then
            rotation = Matrix3dInverse(View.rotation)
            transform = Transform3dFromMatrix3dAndFixedPoint3d(rotation, Point)
            Set MyCell = CreateCellElement2(mComboBox.Text, Point, Point3dOne, True, Matrix3dIdentity)
            MyCell.transform transform
            MyCell.Redraw DrawMode
        ElseIf moveCell = True Then
            Set oClone = MyCell.Clone
            oClone.Redraw msdDrawingModeTemporaryErase
            oClone.Move Point3dSubtract(ActiveDepthDraw(View, bPoint, Point), bPoint)
            oClone.Redraw DrawMode
        ElseIf FirstPoint = True Then
            rotation = Matrix3dInverse(View.rotation)
            Set MyCell = CreateCellElement2(mComboBox.Text, bPoint, Point3dOne, True, rotation)
            MyCell.transform SecondRotate(View, Point)
            MyCell.Redraw DrawMode
        ElseIf FirstPoint = False And Second = True Then '  Крайний поворот
            Set MyCell = CreateCellElement2(mComboBox.Text, bPoint, Point3dOne, True, rotation)
            MyCell.transform SecondRotate(View, ActiveDepthDraw(View, bPoint, Point))
            MyCell.Redraw DrawMode
        
        End If
End Sub

Private Sub IPrimitiveCommandEvents_Keyin(ByVal Keyin As String)

End Sub

Private Sub IPrimitiveCommandEvents_Reset()
    CommandState.StartDefaultCommand
End Sub

Private Sub IPrimitiveCommandEvents_Start()
    CommandState.EnableAccuSnap
    CommandState.StartDynamics
    FirstPoint = False
        If MyForm.CheckBox_cross_view.Value = True Then
            CrossSection CInt(MyForm.ComboBox_inView.Text), CInt(MyForm.ComboBox_CrossView.Text)
        End If
End Sub
Function Point3dToString(pnt As Point3d, myLable As Label) As String
    With pnt
        myLable.Caption = "X= " & Round(.X, 2) & vbCrLf & "Y= " & Round(.Y, 2) & vbCrLf & "Z= " & Round(.Z, 2)
    End With
End Function

Function SecondRotate(dView As View, rotPoint As Point3d) As Transform3d
    Dim plan        As Plane3d
    Dim myRot       As Matrix3d
    Dim pntTemp     As Point3d
    Dim PerpVector  As Vector3d
    Dim tmpVector   As Vector3d
    Dim prBpoint    As Point3d
    
    If FirstPoint = True And Second = False Then
        With fdPoint
            .X = bPoint.X
            .Y = bPoint.Y
            .Z = 0
        End With
    End If
    
    prBpoint = bPoint
    prBpoint.Z = 0
    
    plan.origin = fdPoint
    plan.Normal = dView.rotation.RowZ
    
    If fdPoint.X <> bPoint.X And fdPoint.Y <> bPoint.Y Then
        plan.Normal = Point3dFromVector3d(Vector3dCrossProduct(Vector3dUnitPerpendicularXY(Vector3dFromPoint3d(Point3dSubtract(fdPoint, bPoint))), Vector3dSubtractPoint3dPoint3d(fdPoint, bPoint)))
    End If
    prPointOnPlan = Point3dProjectToPlane3d(rotPoint, plan)
    myRot = Matrix3dFromRotationBetweenVectors(Point3dSubtract(prBpoint, bPoint), Point3dSubtract(prPointOnPlan, bPoint))
    SecondRotate = Transform3dFromMatrix3dAndFixedPoint3d(myRot, bPoint)
    
End Function

Function ActiveDepthDraw(mView As View, aPoint As Point3d, tPoint As Point3d) As Point3d
    Dim mPlan         As Plane3d
    
    With mPlan
        .origin = aPoint
        .Normal = mView.rotation.RowZ
    End With
        ActiveDepthDraw = Point3dProjectToPlane3d(tPoint, mPlan)
End Function

Private Sub CrossSection(inV As Integer, crossV As Integer)
    Dim inView      As View
    Dim crossView   As View
    
    Dim origin      As LineElement
    Dim pP          As Point3d
    Dim pCenter     As Point3d
    
    Set inView = ActiveDesignFile.Views(inV)
    Set crossView = ActiveDesignFile.Views(crossV)
    
    crossView.SetArea Point3dAddPoint3dVector3d(inView.Center, Vector3dRotateXY(Vector3dSubtractPoint3dPoint3d(inView.origin, inView.Center), -Pi / 2)), inView.Extents, Matrix3dFromMatrix3dTimesMatrix3d(inView.rotation, Matrix3dFromAxisAndRotationAngle(2, Pi / 2)), inView.ActiveDepth
    crossView.Center = inView.Center
    crossView.Redraw
End Sub
