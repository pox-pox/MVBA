Attribute VB_Name = "Module1"
Public pMarkers() As Point3d
Public mSegments() As LineElement
Public pMarkerTemp As Point3d
Public index As Long
Public Type dPoints
    mElement As Element
    mPoint As Point3d
End Type


Sub Main()
    UserForm1.Show vbModeless
End Sub

Attribute VB_Name = "PCE_Draw_Marker"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IPrimitiveCommandEvents

Private Sub IPrimitiveCommandEvents_Cleanup()

End Sub

Private Sub IPrimitiveCommandEvents_DataPoint(Point As Point3d, ByVal View As View)

End Sub

Private Sub IPrimitiveCommandEvents_Dynamics(Point As Point3d, ByVal View As View, ByVal DrawMode As MsdDrawingMode)
    Dim mCircle As EllipseElement
    Dim mRadius As Double
    Dim vLine As LineElement
    Dim hLine As LineElement
    Dim hWindow As Double
    Dim wWindow As Double
    Dim mText As TextElement
    
    mRadius = (View.Extents.X + View.Extents.Y) * 0.03
   
    Set hLine = CreateLineElement2(Nothing, Point3dFromXYZ(pMarkerTemp.X + View.Extents.X, pMarkerTemp.Y, pMarkerTemp.Z), Point3dFromXYZ(pMarkerTemp.X - View.Extents.X, pMarkerTemp.Y, pMarkerTemp.Z))
    Set vLine = CreateLineElement2(Nothing, Point3dFromXYZ(pMarkerTemp.X, pMarkerTemp.Y + View.Extents.Y, pMarkerTemp.Z), Point3dFromXYZ(pMarkerTemp.X, pMarkerTemp.Y - View.Extents.Y, pMarkerTemp.Z))
    vLine.Color = 207
    hLine.Color = 207
    
    Set mText = CreateTextElement1(Nothing, "H=" & Round(pMarkerTemp.Z, 2), pMarkerTemp, Matrix3dIdentity)
    mText.Move Point3dFromXYZ(mRadius, mRadius, 0)
    mText.TextStyle.Height = mRadius * 0.3
    mText.TextStyle.Width = mRadius * 0.3
    mText.TextStyle.Justification = msdTextJustificationLeftBottom
    mText.TextStyle.Font = ActiveDesignFile.Fonts("Arial")
    mText.Color = 175
    
    Set mCircle = CreateEllipseElement2(Nothing, pMarkerTemp, mRadius, mRadius, Matrix3dIdentity)
    mCircle.Color = 143
    mCircle.LineWeight = 0
    
    Dim i As Long
    Dim mH As TextElement
    For i = 0 To UBound(pMarkers)
        If i <> index Then
            Set mH = CreateTextElement1(Nothing, "h=" & Round(pMarkers(i).Z, 2), pMarkers(i), Matrix3dIdentity)
            mH.TextStyle.Font = ActiveDesignFile.Fonts("Arial")
            mH.TextStyle.Height = mRadius * 0.2
            mH.TextStyle.Width = mRadius * 0.2
            mH.TextStyle.Justification = msdTextJustificationLeftBottom
            mH.Color = 131
            mH.Redraw DrawMode
        End If
    Next i
    
    mText.Redraw DrawMode
    vLine.Redraw DrawMode
    hLine.Redraw DrawMode
    mCircle.Redraw DrawMode
End Sub

Private Sub IPrimitiveCommandEvents_Keyin(ByVal Keyin As String)

End Sub

Private Sub IPrimitiveCommandEvents_Reset()
    'CommandState.StopDynamics
    CommandState.StartDefaultCommand
End Sub

Private Sub IPrimitiveCommandEvents_Start()
    CommandState.StartDynamics
End Sub

Private Sub DrawElevation(hText As Double)
    Dim i As Long
    Dim mH As TextElement
    
    For i = 0 To UBound(pMarkers)
        Set mH = CreateTextElement1(Nothing, Round(pMarkers(i).Z, 2), pMarkers(i), Matrix3dIdentity)
        mH.TextStyle.Font = ActiveDesignFile.Fonts("Arial")
        mH.TextStyle.Height = hText * 0.1
        mH.TextStyle.Width = hText * 0.1
        mH.TextStyle.Justification = msdTextJustificationLeftBottom
        mH.Color = 124
        
        mH.Redraw DrawMode
    Next i
    
End Sub

Attribute VB_Name = "UserForm1"
Attribute VB_Base = "0{4B086C73-E71A-44BF-80FC-B025D5F17FA7}{2D1AB306-D8A2-48EC-B7CD-8F0BA93D824E}"
Attribute VB_GlobalNameSpace = False
Attribute VB_Creatable = False
Attribute VB_PredeclaredId = True
Attribute VB_Exposed = False
Attribute VB_TemplateDerived = False
Attribute VB_Customizable = False
Private Sub IniLevels(mListBox As ListBox)
    Dim MyLevel As Level
        mListBox.Clear
        For Each MyLevel In ActiveDesignFile.Levels
            If IsElementsOnLevel(MyLevel) Then
                mListBox.AddItem MyLevel.Name
            End If
        Next
End Sub
Private Function IsElementsOnLevel(mLevel As Level) As Boolean
    Dim mEnum As ElementEnumerator
    Dim mFilter As New ElementScanCriteria
    
    mFilter.ExcludeAllLevels
    mFilter.IncludeLevel mLevel
    
    Set mEnum = ActiveModelReference.Scan(mFilter)
    
    If mEnum.MoveNext Then
        IsElementsOnLevel = True
    Else
        IsElementsOnLevel = False
    End If
End Function



Private Sub CheckBox_CheckElevation_Click()
    If CheckBox_CheckElevation.Value = True Then
        Label_k.Enabled = True
        TextBox_round.Enabled = True
    Else
        Label_k.Enabled = False
        TextBox_round.Enabled = False
    End If
End Sub

Private Sub CheckBoxAnalizeZ_Change()
    If CheckBoxAnalizeZ.Value = True Then
        SwitchAnalizeParameters True
    Else
        SwitchAnalizeParameters False
    End If
End Sub

Private Sub SwitchAnalizeParameters(mSwitch As Boolean)
    LabelDtv.Enabled = mSwitch
    LabelLimit.Enabled = mSwitch
    LabelToleranceZ.Enabled = mSwitch
    LabelM.Enabled = mSwitch
    TextBoxMultiSTD.Enabled = mSwitch
    TextBoxZTolerance.Enabled = mSwitch
    TextBoxMaxHeight.Enabled = Not mSwitch
    TextBoxMinHeight.Enabled = Not mSwitch
    CheckBoxMoreH.Enabled = Not mSwitch
    CheckBoxLessH.Enabled = Not mSwitch
    LabelMore.Enabled = Not mSwitch
    LabelLess.Enabled = Not mSwitch
    LabelH.Enabled = Not mSwitch
    LabelHeader.Enabled = Not mSwitch
End Sub

Private Sub CheckBoxMoreH_Change()
    If CheckBoxMoreH.Value = True Then
        TextBoxMinHeight.Enabled = True
        TextBoxMinHeight.Visible = True
        LabelMore.Visible = True
    Else
        TextBoxMinHeight.Enabled = False
        TextBoxMinHeight.Visible = False
        LabelMore.Visible = False
    End If
End Sub
Private Sub CheckBoxLessH_Change()
    If CheckBoxLessH.Value = True Then
        TextBoxMaxHeight.Enabled = True
        TextBoxMaxHeight.Visible = True
        LabelLess.Visible = True
    Else
        TextBoxMaxHeight.Enabled = False
        TextBoxMaxHeight.Visible = False
        LabelLess.Visible = False
    End If
End Sub

Private Sub CommandButton_SetElevation_Click()

End Sub

Private Sub CommandButtonAddMarkersToDgn_Click()
    DrawArrayofMarkers pMarkers
End Sub

Private Sub CommandButtonCheck_Click()
    If CheckBox_CheckElevation.Value = True Then
        SetElevationn
    Else
        DeleteMarkers (TextBoxMarkerLevel.Text)
        Erase pMarkers
        ScanLevels
    End If
End Sub

Private Sub CommandButtonDeleteMarkers_Click()
    DeleteMarkers (TextBoxMarkerLevel.Text)
End Sub

Private Sub CommandButtonShowList_Click()
    UserFormListMarkers.Show vbModeless
End Sub

Private Sub TextBox1_Change()

End Sub

Private Sub UserForm_Initialize()
    IniLevels ListBoxLevesl
End Sub
Sub SetElevation(mElement As Element, elev As Double)
  mElement.Transform Transform3dFromMatrix3dPoint3d(Matrix3dFromScaleFactors(1, 1, 0), Point3dFromXYZ(0, 0, elev))
  mElement.Rewrite
  mElement.Redraw
End Sub

Sub SetElevationn()
    Dim mEnum As ElementEnumerator
    Dim mFilter As New ElementScanCriteria
    Dim mVertex() As Point3d
    Dim i As Long
    Dim a As Double
    Dim avr As Double
    Dim sum As Double
    Dim SKO As Double
    Dim SetElev As Double
    
    
    AddLevelsToFilter mFilter
    AddTypeToFilter mFilter
    
    Set mEnum = ActiveModelReference.Scan(mFilter)
    
    While mEnum.MoveNext
        Erase mVertex
        mVertex = mEnum.Current.AsVertexList.GetVertices
        avr = GetAverageZ(mVertex)
        SetElev = Round(avr / CDbl(UserForm1.TextBox_round.Text), 0) * CDbl(UserForm1.TextBox_round.Text)
        SetElevation mEnum.Current, SetElev
    Wend

End Sub

 Sub ScanLevels()
    Dim mEnum As ElementEnumerator
    Dim mFilter As New ElementScanCriteria
    
    If Not CheckParametersForHeight Then
        UserFormListMarkers.ListBoxListOfMarkers.Clear
        Exit Sub
    End If
    
    AddLevelsToFilter mFilter
    AddTypeToFilter mFilter
    
    Set mEnum = ActiveModelReference.Scan(mFilter)
    
    While mEnum.MoveNext
        Select Case mEnum.Current.Type
            Case msdElementTypeShape
                If CheckBoxAnalizeZ.Value = False Then
                    ReadVertexListShape pMarkers, mEnum.Current.AsShapeElement
                Else
                    FilterVertex pMarkers, mEnum.Current.AsShapeElement
                End If
            Case msdElementTypeComplexShape
                If CheckBoxAnalizeZ.Value = False Then
                    ReadVertexListShape pMarkers, mEnum.Current.AsComplexShapeElement
                Else
                    FilterVertex pMarkers, mEnum.Current.AsShapeElement
                End If
            Case msdElementTypeLineString
                If CheckBoxAnalizeZ.Value = False Then
                    ReadVertexListShape pMarkers, mEnum.Current.AsLineElement
                Else
                    FilterVertex pMarkers, mEnum.Current.AsLineElement
                End If
            Case msdElementTypeLine
                If Not Point3dEqual(mEnum.Current.AsLineElement.StartPoint, mEnum.Current.AsLineElement.EndPoint) Then
                    If CheckBoxAnalizeZ.Value = False Then
                        ReadVertexListShape pMarkers, mEnum.Current.AsLineElement
                    End If
                End If
         End Select
    Wend
    ReporCountMarkers pMarkers
End Sub
Sub FilterVertex(ByRef mPoints() As Point3d, mElement As Element)
    Dim mVertex() As Point3d
    Dim Average As Double
    Dim std As Double
    Dim i As Double
    Dim a As Double
    Dim n As Double
    Dim dz As Double ' Delta Z
    Dim sig As Double
    
    mVertex = mElement.AsVertexList.GetVertices
    n = UBound(mVertex)
    Average = GetAverage(mVertex)
    
    For i = 0 To n - 1
        a = a + (Abs((mVertex(i + 1).Z - mVertex(i).Z)) - Average) ^ 2
    Next i
    std = Sqr(a / n)
    
    For i = 0 To n - 1
        dz = (mVertex(i + 1).Z - mVertex(i).Z)
        sig = CDbl(TextBoxMultiSTD.Text) * std
        Select Case i
            Case 0 ' Первый вертекс
                If Not ((Abs(dz) >= Average - sig) And (Abs(dz) <= Average + sig)) Then
                    If Abs(Average - dz) > CDbl(TextBoxZTolerance.Text) Then
                        AddPointToArray mPoints, mVertex(i)
                    End If
                End If
            Case n - 1 ' Последний вертекс
                If Not ((Abs(dz) >= Average - sig) And (Abs(dz) <= Average + sig)) Then
                    If Abs(Average - dz) > CDbl(TextBoxZTolerance.Text) Then
                        AddPointToArray mPoints, mVertex(i + 1)
                    End If
                End If
            Case Else ' Остальные вертексы
                If Not ((Abs(dz) >= Average - sig) And (Abs(dz) <= Average + sig)) Then
                    If Abs(Average - dz) > CDbl(TextBoxZTolerance.Text) Then
                    
                        dz = (mVertex(i + 2).Z - mVertex(i + 1).Z)
                        If Not ((Abs(dz) >= Average - sig) And (Abs(dz) <= Average + sig)) Then
                            If Abs(Average - dz) > CDbl(TextBoxZTolerance.Text) Then
                                AddPointToArray mPoints, mVertex(i + 1)
                                i = i + 1
                            End If
                        ElseIf ((Abs(dz) >= Average - sig) And (Abs(dz) <= Average + sig)) Then
                            AddPointToArray mPoints, mVertex(i)
                            AddPointToArray mPoints, mVertex(i + 1)
                        End If
                    End If
                End If
        End Select
    Next i
End Sub
Private Sub DrawLine(pS As Point3d, pE As Point3d)
    Dim mLine As LineElement
    
    Set mLine = CreateLineElement2(Nothing, pS, pE)
    mLine.Color = 3
    mLine.LineWeight = 4
    ActiveModelReference.AddElement mLine
    mLine.Redraw
End Sub
Private Function GetAverageZ(mVertex() As Point3d) As Double
    Dim i As Long
    Dim Avrg As Double
    
    
    For i = 0 To UBound(mVertex) - 1
        Avrg = Avrg + mVertex(i).Z
    Next i
    Avrg = Avrg / UBound(mVertex)
    
    GetAverageZ = Avrg
End Function
Private Function GetAverage(mVertex() As Point3d) As Double
    Dim i As Long
    Dim Avrg As Double
    
    
    For i = 0 To UBound(mVertex) - 1
        Avrg = Avrg + Abs(mVertex(i + 1).Z - mVertex(i).Z)
    Next i
    Avrg = Avrg / UBound(mVertex)
    
    GetAverage = Avrg
End Function
Private Sub ReporCountMarkers(ByRef mArray() As Point3d)
    Dim u As Long
    Dim i As Long
    
    On Error Resume Next
    u = UBound(mArray) + 1
    If Err.Number = 9 Then
        ReDim mArray(0)
        u = 0
        MsgBox "Вертексов не найдено"
        Exit Sub
    End If
    Err.Clear
    
    Response = MsgBox("Записать маркеры в DGN?", vbYesNo + vbDefaultButton1, "Найдено вертексов: " & u & " шт.")
    If Response = vbYes Then    ' User chose Yes.
        For i = 0 To UBound(mArray)
            DrawMarker mArray(i)
            UserFormListMarkers.Show vbModeless
            InizialiseListMarkers mArray, UserFormListMarkers.ListBoxListOfMarkers
        Next i
    Else    ' User chose No.
           UserFormListMarkers.Show vbModeless
           InizialiseListMarkers mArray, UserFormListMarkers.ListBoxListOfMarkers
    End If
End Sub

Private Sub DrawArrayofMarkers(mArray() As Point3d)
    Dim u As Long
    Dim i As Long
    
    On Error Resume Next
    u = UBound(mArray)
    If Err.Number = 9 Then
        MsgBox "Список вертексов пуст"
        Exit Sub
    End If
    Err.Clear
    
    For i = 0 To u
        DrawMarker mArray(i)
    Next i
End Sub
Sub InizialiseListMarkers(mMarkers() As Point3d, mListBox As ListBox)
    Dim i As Long
    
    mListBox.Clear
        For i = 0 To UBound(mMarkers)
            mListBox.AddItem FormatNumber(Round(mMarkers(i).Z, 2), 2, vbTrue, vbTrue, vbFalse)
        Next i
End Sub

Private Sub ReadVertexListShape(ByRef mPoints() As Point3d, mVertexList As Element)
    Dim i As Long
    Dim mVertex() As Point3d
    
    mVertex = mVertexList.AsVertexList.GetVertices
    
    For i = 0 To UBound(mVertex)
        If CheckBoxMoreH.Value = True And CheckBoxLessH.Value = True Then
            If CDbl(TextBoxMinHeight.Text) = CDbl(TextBoxMaxHeight.Text) Then
                If mVertex(i).Z = CDbl(TextBoxMinHeight.Text) Then
                    AddPointToArray mPoints, mVertex(i)
                End If
            ElseIf CDbl(TextBoxMinHeight.Text) < CDbl(TextBoxMaxHeight.Text) Then
                If mVertex(i).Z > CDbl(TextBoxMinHeight.Text) And mVertex(i).Z < CDbl(TextBoxMaxHeight.Text) Then
                    AddPointToArray mPoints, mVertex(i)
                End If
            ElseIf CDbl(TextBoxMinHeight.Text) > CDbl(TextBoxMaxHeight.Text) Then
                MsgBox "Мимальное значение не может быть больше максимального", vbCritical
                Exit Sub
            End If
        ElseIf CheckBoxMoreH.Value = True Then
            If mVertex(i).Z > CDbl(TextBoxMinHeight.Text) Then
                AddPointToArray mPoints, mVertex(i)
            End If
        ElseIf CheckBoxLessH.Value = True Then
            If mVertex(i).Z < CDbl(TextBoxMaxHeight.Text) Then
                AddPointToArray mPoints, mVertex(i)
            End If
        ElseIf CheckBoxMoreH.Value = False And CheckBoxLessH.Value = False Then
            MsgBox "Задайте параметры поиска высот", vbInformation
            Exit Sub
        End If
    Next i
End Sub

Private Sub AddPointToArray(ByRef mArray() As Point3d, mPoint As Point3d)
    Dim u As Long
    
    On Error Resume Next
    u = UBound(mArray) + 1
    If Err.Number = 9 Then
        ReDim mArray(0)
        u = 0
    End If
    Err.Clear
    ReDim Preserve mArray(u)
    mArray(u) = mPoint
    
End Sub
Private Function CheckParametersForHeight() As Boolean
    Dim pReturne As Boolean
    pReturne = True
    If (CDbl(TextBoxMinHeight.Text) > CDbl(TextBoxMaxHeight.Text)) And (CheckBoxMoreH.Value = True And CheckBoxLessH.Value = True) Then
         MsgBox "Мимальное значение ВЫСОТЫ не может быть больше максимального", vbCritical
         pReturne = False
    ElseIf CheckBoxMoreH.Value = False And CheckBoxLessH.Value = False Then
        MsgBox "Задайте параметры поиска высот", vbInformation
        pReturne = False
    ElseIf Not IsSelectedListbox(ListBoxLevesl) Then
        MsgBox "Выберете слой для поиска", vbInformation
        pReturne = False
    End If
    CheckParametersForHeight = pReturne
End Function
Private Function IsSelectedListbox(mListBox As ListBox) As Boolean
    Dim i As Long
    
    IsSelectedListbox = False
    
    For i = 1 To ListBoxLevesl.ListCount
        If ListBoxLevesl.Selected(i - 1) Then
            IsSelectedListbox = True
            Exit Function
        End If
    Next i
End Function
Private Sub DrawMarker(mPoint As Point3d)
    Dim mMarker As EllipseElement
    Dim r As Long
    
    r = CDbl(TextBoxSizeMarker.Text)
    
    Set mMarker = CreateEllipseElement2(Nothing, mPoint, r, r, Matrix3dIdentity)
    mMarker.Level = CheckLevel(TextBoxMarkerLevel.Text)
    mMarker.Color = CLng(TextBoxColorMarker.Text)
    ActiveModelReference.AddElement mMarker
    mMarker.Redraw
    
End Sub
Private Sub DeleteMarkers(slevel As String)
    Dim mEnum As ElementEnumerator
    Dim mFilter As New ElementScanCriteria
    Dim mLevel As Level
        
    On Error Resume Next
    Set mLevel = ActiveDesignFile.Levels(slevel)
    If Err.Number = 5 Or Err.Number = -2147024809 Then
        Err.Clear
        Exit Sub
    End If
    mFilter.ExcludeAllLevels
    mFilter.IncludeLevel mLevel
    
    Set mEnum = ActiveModelReference.Scan(mFilter)
    
    While mEnum.MoveNext
        ActiveModelReference.RemoveElement mEnum.Current
        mEnum.Current.Redraw
    Wend
    ActiveDesignFile.DeleteLevel mLevel
    ActiveDesignFile.Levels.Rewrite
End Sub
Function CheckLevel(LevelName As String) As Level
    Dim MyLevel As Level
    On Error Resume Next
    
    Set CheckLevel = ActiveDesignFile.Levels(LevelName)
    If Err.Number <> 0 And LevelName <> "" Then
         Set MyLevel = ActiveDesignFile.AddNewLevel(LevelName)
         ActiveDesignFile.Levels.Rewrite
         MsgBox "Создан слой: " & LevelName
         Set CheckLevel = MyLevel
    End If
    Err.Clear
End Function

Private Sub AddTypeToFilter(ByRef mFilter As ElementScanCriteria)
    
    mFilter.IncludeType msdElementTypeShape
    mFilter.IncludeType msdElementTypeComplexShape
    mFilter.IncludeType msdElementTypeLine
    mFilter.IncludeType msdElementTypeLineString
End Sub
Private Sub AddLevelsToFilter(ByRef mFilter As ElementScanCriteria)
    Dim i As Long
    
    mFilter.ExcludeAllLevels
    
    For i = 1 To ListBoxLevesl.ListCount
        If ListBoxLevesl.Selected(i - 1) Then
            mFilter.IncludeLevel ActiveDesignFile.Levels(ListBoxLevesl.List(i - 1))
        End If
    Next i
End Sub

Attribute VB_Name = "UserFormListMarkers"
Attribute VB_Base = "0{18A608F4-F572-4E5C-AB15-9B64D8DAB2C7}{6E2B00DE-93E3-485D-B1B3-E80C00ABE38C}"
Attribute VB_GlobalNameSpace = False
Attribute VB_Creatable = False
Attribute VB_PredeclaredId = True
Attribute VB_Exposed = False
Attribute VB_TemplateDerived = False
Attribute VB_Customizable = False
Private Sub CommandButtonReload_Click()
    Erase pMarkers
    UserForm1.ScanLevels
    UserForm1.InizialiseListMarkers pMarkers, ListBoxListOfMarkers
End Sub

Private Sub ListBoxListOfMarkers_Change()
    Dim i As Long
    
    i = GetIndexSelected(ListBoxListOfMarkers)
    MoveView 1, pMarkers(i)
    DrawMarker i
    
End Sub

Private Sub UserForm_QueryClose(Cancel As Integer, CloseMode As Integer)
   Cancel = 1
   UserFormListMarkers.Hide
End Sub


Private Sub MoveView(i As Integer, mPoint As Point3d)
    Dim pCenter As Point3d
    
    ActiveDesignFile.Views(i).Center = mPoint
    ActiveDesignFile.Views(i).Redraw
End Sub

Private Function GetIndexSelected(mListBox As ListBox) As Long
    Dim i As Long
    
    For i = 1 To mListBox.ListCount
        If mListBox.Selected(i - 1) Then
            GetIndexSelected = i - 1
            Exit Function
        End If
    Next i
End Function

Private Sub DrawMarker(i As Long)
    Dim mMark As New PCE_Draw_Marker
    pMarkerTemp = pMarkers(i)
    index = i
    CommandState.StartPrimitive mMark
End Sub
